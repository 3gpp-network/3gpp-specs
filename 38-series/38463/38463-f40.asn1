E1AP-PDU-Descriptions {
itu-t (0) identified-organization (4) etsi (0) mobileDomain (0)
ngran-access (22) modules (3) e1ap (5) version1 (1) e1ap-PDU-Descriptions (0) }

DEFINITIONS AUTOMATIC TAGS ::= 

BEGIN







IMPORTS
	Criticality,
	ProcedureCode

FROM E1AP-CommonDataTypes
	Reset,
	ResetAcknowledge,
	ErrorIndication,
	GNB-CU-UP-E1SetupRequest,
	GNB-CU-UP-E1SetupResponse,
	GNB-CU-UP-E1SetupFailure, 
	GNB-CU-CP-E1SetupRequest,
	GNB-CU-CP-E1SetupResponse,
	GNB-CU-CP-E1SetupFailure, 
	GNB-CU-UP-ConfigurationUpdate,
	GNB-CU-UP-ConfigurationUpdateAcknowledge,
	GNB-CU-UP-ConfigurationUpdateFailure,
	GNB-CU-CP-ConfigurationUpdate,
	GNB-CU-CP-ConfigurationUpdateAcknowledge,
	GNB-CU-CP-ConfigurationUpdateFailure,
	BearerContextSetupRequest,
	BearerContextSetupResponse,
	BearerContextSetupFailure,
	BearerContextModificationRequest,
	BearerContextModificationResponse,
	BearerContextModificationFailure,
	BearerContextModificationRequired,
	BearerContextModificationConfirm,
	BearerContextReleaseCommand,
	BearerContextReleaseComplete,
	BearerContextReleaseRequest,
	BearerContextInactivityNotification,
	DLDataNotification,
	ULDataNotification,
	DataUsageReport,
	E1ReleaseRequest,
	E1ReleaseResponse,
	GNB-CU-UP-CounterCheckRequest,
	GNB-CU-UP-StatusIndication,
	MRDC-DataUsageReport,
	PrivateMessage

FROM E1AP-PDU-Contents
	id-reset,
	id-errorIndication,
	id-gNB-CU-UP-E1Setup,
	id-gNB-CU-CP-E1Setup,
	id-gNB-CU-UP-ConfigurationUpdate,
	id-gNB-CU-CP-ConfigurationUpdate,
	id-e1Release,
	id-bearerContextSetup,
	id-bearerContextModification,
	id-bearerContextModificationRequired,
	id-bearerContextRelease,
	id-bearerContextReleaseRequest,
	id-bearerContextInactivityNotification,
	id-dLDataNotification,
	id-uLDataNotification,
	id-dataUsageReport,
	id-gNB-CU-UP-CounterCheck,
	id-gNB-CU-UP-StatusIndication,
	id-mRDC-DataUsageReport,
	id-privateMessage

FROM E1AP-Constants;







E1AP-ELEMENTARY-PROCEDURE ::= CLASS {
	&InitiatingMessage				,
	&SuccessfulOutcome							OPTIONAL,
	
&UnsuccessfulOutcome						OPTIONAL,
	&procedureCode				ProcedureCode 	UNIQUE,
	&criticality				Criticality 	DEFAULT ignore
}
WITH SYNTAX {
	INITIATING MESSAGE			&InitiatingMessage
	[SUCCESSFUL OUTCOME			&SuccessfulOutcome]
	[UNSUCCESSFUL OUTCOME		&UnsuccessfulOutcome]
	PROCEDURE CODE				&procedureCode
	[CRITICALITY				&criticality]
}







E1AP-PDU ::= CHOICE {
	initiatingMessage		InitiatingMessage,
	successfulOutcome		SuccessfulOutcome,
	unsuccessfulOutcome		UnsuccessfulOutcome,
	...
}

InitiatingMessage ::= SEQUENCE {
	procedureCode			E1AP-ELEMENTARY-PROCEDURE.&procedureCode		({E1AP-ELEMENTARY-PROCEDURES}),
	criticality				E1AP-ELEMENTARY-PROCEDURE.&criticality			({E1AP-ELEMENTARY-PROCEDURES}{@procedureCode}),
	value					E1AP-ELEMENTARY-PROCEDURE.&InitiatingMessage	({E1AP-ELEMENTARY-PROCEDURES}{@procedureCode})
}

SuccessfulOutcome ::= SEQUENCE {
	procedureCode			E1AP-ELEMENTARY-PROCEDURE.&procedureCode		({E1AP-ELEMENTARY-PROCEDURES}),
	criticality				E1AP-ELEMENTARY-PROCEDURE.&criticality			({E1AP-ELEMENTARY-PROCEDURES}{@procedureCode}),
	value					E1AP-ELEMENTARY-PROCEDURE.&SuccessfulOutcome	({E1AP-ELEMENTARY-PROCEDURES}{@procedureCode})
}

UnsuccessfulOutcome ::= SEQUENCE {
	procedureCode			E1AP-ELEMENTARY-PROCEDURE.&procedureCode		({E1AP-ELEMENTARY-PROCEDURES}),
	criticality				E1AP-ELEMENTARY-PROCEDURE.&criticality			({E1AP-ELEMENTARY-PROCEDURES}{@procedureCode}),
	value					E1AP-ELEMENTARY-PROCEDURE.&UnsuccessfulOutcome	({E1AP-ELEMENTARY-PROCEDURES}{@procedureCode})
}







E1AP-ELEMENTARY-PROCEDURES E1AP-ELEMENTARY-PROCEDURE ::= {
	E1AP-ELEMENTARY-PROCEDURES-CLASS-1			|
	E1AP-ELEMENTARY-PROCEDURES-CLASS-2			,

	...
}

E1AP-ELEMENTARY-PROCEDURES-CLASS-1 E1AP-ELEMENTARY-PROCEDURE ::= {
	reset										|
	gNB-CU-UP-E1Setup							|
	gNB-CU-CP-E1Setup							|
	gNB-CU-UP-ConfigurationUpdate				|
	gNB-CU-CP-ConfigurationUpdate				|
	e1Release									|
	bearerContextSetup							|
	bearerContextModification					|
	bearerContextModificationRequired			|
	bearerContextRelease						,
	...
}

E1AP-ELEMENTARY-PROCEDURES-CLASS-2 E1AP-ELEMENTARY-PROCEDURE ::= {
	errorIndication							|
	bearerContextReleaseRequest				|
	bearerContextInactivityNotification		|
	dLDataNotification						|
	uLDataNotification						|
	dataUsageReport							|
	gNB-CU-UP-CounterCheck					|
	gNB-CU-UP-StatusIndication			|
	mRDC-DataUsageReport					|
	privateMessage							,
	...
}







reset E1AP-ELEMENTARY-PROCEDURE ::= {
	INITIATING MESSAGE		Reset
	SUCCESSFUL OUTCOME		ResetAcknowledge
	PROCEDURE CODE			id-reset
	CRITICALITY				reject
}

errorIndication E1AP-ELEMENTARY-PROCEDURE ::= {
	INITIATING MESSAGE		ErrorIndication
	PROCEDURE CODE			id-errorIndication
	CRITICALITY				ignore
}

gNB-CU-UP-E1Setup E1AP-ELEMENTARY-PROCEDURE ::= {
	INITIATING MESSAGE		GNB-CU-UP-E1SetupRequest
	SUCCESSFUL OUTCOME		GNB-CU-UP-E1SetupResponse
	UNSUCCESSFUL OUTCOME	GNB-CU-UP-E1SetupFailure
	PROCEDURE CODE			id-gNB-CU-UP-E1Setup
	CRITICALITY				reject
}

gNB-CU-CP-E1Setup E1AP-ELEMENTARY-PROCEDURE ::= {
	INITIATING MESSAGE		GNB-CU-CP-E1SetupRequest
	SUCCESSFUL OUTCOME		GNB-CU-CP-E1SetupResponse
	UNSUCCESSFUL OUTCOME	GNB-CU-CP-E1SetupFailure
	PROCEDURE CODE			id-gNB-CU-CP-E1Setup
	CRITICALITY				reject
}

gNB-CU-UP-ConfigurationUpdate E1AP-ELEMENTARY-PROCEDURE ::= {
	INITIATING MESSAGE		GNB-CU-UP-ConfigurationUpdate
	SUCCESSFUL OUTCOME		GNB-CU-UP-ConfigurationUpdateAcknowledge
	UNSUCCESSFUL OUTCOME	GNB-CU-UP-ConfigurationUpdateFailure
	PROCEDURE CODE			id-gNB-CU-UP-ConfigurationUpdate
	CRITICALITY				reject
}

gNB-CU-CP-ConfigurationUpdate E1AP-ELEMENTARY-PROCEDURE ::= {
	INITIATING MESSAGE		GNB-CU-CP-ConfigurationUpdate
	SUCCESSFUL OUTCOME		GNB-CU-CP-ConfigurationUpdateAcknowledge
	UNSUCCESSFUL OUTCOME	GNB-CU-CP-ConfigurationUpdateFailure
	PROCEDURE CODE			id-gNB-CU-CP-ConfigurationUpdate
	CRITICALITY				reject
}

e1Release E1AP-ELEMENTARY-PROCEDURE ::= {
	INITIATING MESSAGE		E1ReleaseRequest
	SUCCESSFUL OUTCOME		E1ReleaseResponse
	PROCEDURE CODE			id-e1Release
	CRITICALITY				reject
}

bearerContextSetup E1AP-ELEMENTARY-PROCEDURE ::= {
	INITIATING MESSAGE		BearerContextSetupRequest
	SUCCESSFUL OUTCOME		BearerContextSetupResponse
	UNSUCCESSFUL OUTCOME	BearerContextSetupFailure
	PROCEDURE CODE			id-bearerContextSetup
	CRITICALITY				reject
}

bearerContextModification E1AP-ELEMENTARY-PROCEDURE ::= {
	INITIATING MESSAGE		BearerContextModificationRequest
	SUCCESSFUL OUTCOME		BearerContextModificationResponse
	UNSUCCESSFUL OUTCOME	BearerContextModificationFailure
	PROCEDURE CODE			id-bearerContextModification
	CRITICALITY				reject
}

bearerContextModificationRequired E1AP-ELEMENTARY-PROCEDURE ::= {
	INITIATING MESSAGE		BearerContextModificationRequired
	SUCCESSFUL OUTCOME		BearerContextModificationConfirm
	PROCEDURE CODE			id-bearerContextModificationRequired
	CRITICALITY				reject
}

bearerContextRelease E1AP-ELEMENTARY-PROCEDURE ::= {
	INITIATING MESSAGE		BearerContextReleaseCommand
	SUCCESSFUL OUTCOME		BearerContextReleaseComplete
	PROCEDURE CODE			id-bearerContextRelease
	CRITICALITY				reject
}

bearerContextReleaseRequest E1AP-ELEMENTARY-PROCEDURE ::= {
	INITIATING MESSAGE		BearerContextReleaseRequest
	PROCEDURE CODE			id-bearerContextReleaseRequest
	CRITICALITY				ignore
}

bearerContextInactivityNotification E1AP-ELEMENTARY-PROCEDURE ::= {
	INITIATING MESSAGE		BearerContextInactivityNotification
	PROCEDURE CODE			id-bearerContextInactivityNotification
	CRITICALITY				ignore
}

dLDataNotification E1AP-ELEMENTARY-PROCEDURE ::= {
	INITIATING MESSAGE		DLDataNotification
	PROCEDURE CODE			id-dLDataNotification
	CRITICALITY				ignore
}

uLDataNotification E1AP-ELEMENTARY-PROCEDURE ::= {
	INITIATING MESSAGE		ULDataNotification
	PROCEDURE CODE			id-uLDataNotification
	CRITICALITY				ignore
}

dataUsageReport E1AP-ELEMENTARY-PROCEDURE ::= {
	INITIATING MESSAGE		DataUsageReport
	PROCEDURE CODE			id-dataUsageReport
	CRITICALITY				ignore
}

gNB-CU-UP-CounterCheck E1AP-ELEMENTARY-PROCEDURE ::= {
	INITIATING MESSAGE		GNB-CU-UP-CounterCheckRequest
	PROCEDURE CODE			id-gNB-CU-UP-CounterCheck
	CRITICALITY				ignore
}

gNB-CU-UP-StatusIndication 	E1AP-ELEMENTARY-PROCEDURE ::= {
	INITIATING MESSAGE		GNB-CU-UP-StatusIndication
	PROCEDURE CODE			id-gNB-CU-UP-StatusIndication
	CRITICALITY			ignore
}

privateMessage E1AP-ELEMENTARY-PROCEDURE ::= {
	INITIATING MESSAGE		PrivateMessage
	PROCEDURE CODE			id-privateMessage
	CRITICALITY				ignore
}

mRDC-DataUsageReport	E1AP-ELEMENTARY-PROCEDURE ::= {
	INITIATING MESSAGE		MRDC-DataUsageReport
	PROCEDURE CODE			id-mRDC-DataUsageReport
	CRITICALITY				ignore
}

END







E1AP-PDU-Contents {
itu-t (0) identified-organization (4) etsi (0) mobileDomain (0)
ngran-access (22) modules (3) e1ap (5) version1 (1) e1ap-PDU-Contents (1) }

DEFINITIONS AUTOMATIC TAGS ::= 

BEGIN







IMPORTS
	
	Cause,
	CriticalityDiagnostics,
	GNB-CU-CP-UE-E1AP-ID,
	GNB-CU-UP-UE-E1AP-ID,
	UE-associatedLogicalE1-ConnectionItem,
	GNB-CU-UP-ID,
	GNB-CU-UP-Name,
	GNB-CU-CP-Name,
	CNSupport,
	PLMN-Identity,
	Slice-Support-List,
	NR-CGI-Support-List,
	QoS-Parameters-Support-List,
	SecurityInformation,
	BitRate,
	BearerContextStatusChange,
	DRB-To-Setup-List-EUTRAN,
	DRB-Setup-List-EUTRAN,
	DRB-Failed-List-EUTRAN,
	DRB-To-Modify-List-EUTRAN,
	DRB-Modified-List-EUTRAN,
	DRB-Failed-To-Modify-List-EUTRAN,
	DRB-To-Remove-List-EUTRAN,
	DRB-Required-To-Remove-List-EUTRAN,
	DRB-Required-To-Modify-List-EUTRAN,
	DRB-Confirm-Modified-List-EUTRAN,
	DRB-To-Setup-Mod-List-EUTRAN,
	DRB-Setup-Mod-List-EUTRAN,
	DRB-Failed-Mod-List-EUTRAN,
	PDU-Session-Resource-To-Setup-List,
	PDU-Session-Resource-Setup-List,
	PDU-Session-Resource-Failed-List,
	PDU-Session-Resource-To-Modify-List,
	PDU-Session-Resource-Modified-List,
	PDU-Session-Resource-Failed-To-Modify-List,
	PDU-Session-Resource-To-Remove-List,
	PDU-Session-Resource-Required-To-Modify-List,
	PDU-Session-Resource-Confirm-Modified-List,
	PDU-Session-Resource-To-Setup-Mod-List,
	PDU-Session-Resource-Setup-Mod-List,
	PDU-Session-Resource-Failed-Mod-List,
	PDU-Session-To-Notify-List,
	DRB-Status-Item,
	DRB-Activity-Item,
	Data-Usage-Report-List,
	TimeToWait,
	ActivityNotificationLevel,
	ActivityInformation,
	New-UL-TNL-Information-Required,
	GNB-CU-CP-TNLA-Setup-Item,
	GNB-CU-CP-TNLA-Failed-To-Setup-Item,
	GNB-CU-CP-TNLA-To-Add-Item,
	GNB-CU-CP-TNLA-To-Remove-Item,
	GNB-CU-CP-TNLA-To-Update-Item,
	GNB-CU-UP-TNLA-To-Remove-Item,
	TransactionID,
	Inactivity-Timer,
	DRBs-Subject-To-Counter-Check-List-EUTRAN,
	DRBs-Subject-To-Counter-Check-List-NG-RAN,
	PPI,
	GNB-CU-UP-Capacity,
	GNB-CU-UP-OverloadInformation,
	DataDiscardRequired,
	PDU-Session-Resource-Data-Usage-List,
	RANUEID,
	GNB-DU-ID


FROM E1AP-IEs

	PrivateIE-Container{},
	ProtocolExtensionContainer{},
	ProtocolIE-Container{},
	ProtocolIE-ContainerList{},
	ProtocolIE-SingleContainer{},
	E1AP-PRIVATE-IES,
	E1AP-PROTOCOL-EXTENSION,
	E1AP-PROTOCOL-IES


FROM E1AP-Containers
	
	id-Cause,
	id-CriticalityDiagnostics,
	id-gNB-CU-CP-UE-E1AP-ID, 
	id-gNB-CU-UP-UE-E1AP-ID,
	id-ResetType,
	id-UE-associatedLogicalE1-ConnectionItem,
	id-UE-associatedLogicalE1-ConnectionListResAck,
	id-gNB-CU-UP-ID,
	id-gNB-CU-UP-Name,
	id-gNB-CU-CP-Name,
	id-CNSupport,
	id-SupportedPLMNs,
	id-SecurityInformation,
	id-UEDLAggregateMaximumBitRate,
	id-BearerContextStatusChange,
	id-System-BearerContextSetupRequest,
	id-System-BearerContextSetupResponse,
	id-System-BearerContextModificationRequest,
	id-System-BearerContextModificationResponse,
	id-System-BearerContextModificationConfirm,
	id-System-BearerContextModificationRequired,
	id-DRB-Status-List,
	id-Data-Usage-Report-List,	
	id-TimeToWait,
	id-ActivityNotificationLevel,
	id-ActivityInformation,
	id-New-UL-TNL-Information-Required,
	id-GNB-CU-CP-TNLA-Setup-List,
	id-GNB-CU-CP-TNLA-Failed-To-Setup-List,
	id-GNB-CU-CP-TNLA-To-Add-List,
	id-GNB-CU-CP-TNLA-To-Remove-List,
	id-GNB-CU-CP-TNLA-To-Update-List,
	id-GNB-CU-UP-TNLA-To-Remove-List,
	id-DRB-To-Setup-List-EUTRAN,
	id-DRB-To-Modify-List-EUTRAN,
	id-DRB-To-Remove-List-EUTRAN,
	id-DRB-Required-To-Modify-List-EUTRAN,
	id-DRB-Required-To-Remove-List-EUTRAN,
	id-DRB-Setup-List-EUTRAN,
	id-DRB-Failed-List-EUTRAN,
	id-DRB-Modified-List-EUTRAN,
	id-DRB-Failed-To-Modify-List-EUTRAN,
	id-DRB-Confirm-Modified-List-EUTRAN,
	id-DRB-To-Setup-Mod-List-EUTRAN,
	id-DRB-Setup-Mod-List-EUTRAN,
	id-DRB-Failed-Mod-List-EUTRAN,
	id-PDU-Session-Resource-To-Setup-List,
	id-PDU-Session-Resource-To-Modify-List,
	id-PDU-Session-Resource-To-Remove-List,
	id-PDU-Session-Resource-Required-To-Modify-List,
	id-PDU-Session-Resource-Setup-List,
	id-PDU-Session-Resource-Failed-List,
	id-PDU-Session-Resource-Modified-List,
	id-PDU-Session-Resource-Failed-To-Modify-List,
	id-PDU-Session-Resource-Confirm-Modified-List,
	id-PDU-Session-Resource-Setup-Mod-List,
	id-PDU-Session-Resource-Failed-Mod-List,
	id-PDU-Session-Resource-To-Setup-Mod-List,
	id-PDU-Session-To-Notify-List,
	id-TransactionID,
	id-Serving-PLMN,
	id-UE-Inactivity-Timer,
	id-System-GNB-CU-UP-CounterCheckRequest,
	id-DRBs-Subject-To-Counter-Check-List-EUTRAN,
	id-DRBs-Subject-To-Counter-Check-List-NG-RAN,
	id-PPI,
	id-gNB-CU-UP-Capacity,
	id-GNB-CU-UP-OverloadInformation,
	id-UEDLMaximumIntegrityProtectedDataRate,
	id-DataDiscardRequired,
	id-PDU-Session-Resource-Data-Usage-List,
	id-RANUEID,
	id-GNB-DU-ID,

	maxnoofErrors,
	maxnoofSPLMNs,
	maxnoofDRBs,
	maxnoofTNLAssociations,
	maxnoofIndividualE1ConnectionsToReset

	
FROM E1AP-Constants;













Reset ::= SEQUENCE {
	protocolIEs			ProtocolIE-Container       { {ResetIEs} },
	...
}

ResetIEs E1AP-PROTOCOL-IES ::= { 
	{ ID id-TransactionID				CRITICALITY reject	TYPE TransactionID				PRESENCE mandatory	}|
	{ ID id-Cause						CRITICALITY ignore	TYPE Cause						PRESENCE mandatory	}|
	{ ID id-ResetType					CRITICALITY reject	TYPE ResetType					PRESENCE mandatory	},
	...
}

ResetType ::= CHOICE {
	e1-Interface					ResetAll,
	partOfE1-Interface				UE-associatedLogicalE1-ConnectionListRes,
	choice-extension				ProtocolIE-SingleContainer	{{ResetType-ExtIEs}}
}

ResetType-ExtIEs E1AP-PROTOCOL-IES ::= {
	...
}

ResetAll ::= ENUMERATED {
	reset-all,
	...
}

UE-associatedLogicalE1-ConnectionListRes ::= SEQUENCE (SIZE(1.. maxnoofIndividualE1ConnectionsToReset)) OF ProtocolIE-SingleContainer { { UE-associatedLogicalE1-ConnectionItemRes } }

UE-associatedLogicalE1-ConnectionItemRes E1AP-PROTOCOL-IES ::= {
	
	{ ID id-UE-associatedLogicalE1-ConnectionItem	CRITICALITY reject	TYPE UE-associatedLogicalE1-ConnectionItem	PRESENCE mandatory},
	...
}







ResetAcknowledge ::= SEQUENCE {
	protocolIEs			ProtocolIE-Container       { {ResetAcknowledgeIEs} },
	...
}

ResetAcknowledgeIEs E1AP-PROTOCOL-IES ::= {
	{ ID id-TransactionID									CRITICALITY reject	TYPE TransactionID				PRESENCE mandatory	}|
	{ ID id-UE-associatedLogicalE1-ConnectionListResAck		CRITICALITY ignore	TYPE UE-associatedLogicalE1-ConnectionListResAck			PRESENCE optional	}|
	{ ID id-CriticalityDiagnostics		CRITICALITY ignore	TYPE CriticalityDiagnostics			PRESENCE optional	},
	...
}

UE-associatedLogicalE1-ConnectionListResAck ::= SEQUENCE (SIZE(1.. maxnoofIndividualE1ConnectionsToReset)) OF ProtocolIE-SingleContainer { { UE-associatedLogicalE1-ConnectionItemResAck } }

UE-associatedLogicalE1-ConnectionItemResAck 	E1AP-PROTOCOL-IES ::= {
	{ ID id-UE-associatedLogicalE1-ConnectionItem	 CRITICALITY ignore 	TYPE UE-associatedLogicalE1-ConnectionItem  	PRESENCE mandatory },
	...
}








ErrorIndication ::= SEQUENCE {
	protocolIEs		ProtocolIE-Container	{{ErrorIndication-IEs}},
	...
}

ErrorIndication-IEs E1AP-PROTOCOL-IES ::= {
	{ ID id-TransactionID					CRITICALITY reject	TYPE TransactionID				PRESENCE mandatory	}|
	{ ID id-gNB-CU-CP-UE-E1AP-ID			CRITICALITY ignore	TYPE GNB-CU-CP-UE-E1AP-ID		PRESENCE optional}|
	{ ID id-gNB-CU-UP-UE-E1AP-ID			CRITICALITY ignore	TYPE GNB-CU-UP-UE-E1AP-ID		PRESENCE optional}|	
	{ ID id-Cause							CRITICALITY ignore	TYPE Cause						PRESENCE optional}|
	{ ID id-CriticalityDiagnostics			CRITICALITY ignore	TYPE CriticalityDiagnostics		PRESENCE optional},
	...
}













GNB-CU-UP-E1SetupRequest ::= SEQUENCE {
	protocolIEs			ProtocolIE-Container       { {GNB-CU-UP-E1SetupRequestIEs} },
	...
}

GNB-CU-UP-E1SetupRequestIEs E1AP-PROTOCOL-IES ::= {
	{ ID id-TransactionID						CRITICALITY reject	TYPE TransactionID					PRESENCE mandatory	}|
	{ ID id-gNB-CU-UP-ID						CRITICALITY reject	TYPE GNB-CU-UP-ID					PRESENCE mandatory	}|
	{ ID id-gNB-CU-UP-Name						CRITICALITY ignore	TYPE GNB-CU-UP-Name					PRESENCE optional	}|
	{ ID id-CNSupport							CRITICALITY reject	TYPE CNSupport						PRESENCE mandatory	}|
	{ ID id-SupportedPLMNs						CRITICALITY reject	TYPE SupportedPLMNs-List			PRESENCE mandatory	}|
	{ ID id-gNB-CU-UP-Capacity					CRITICALITY ignore	TYPE GNB-CU-UP-Capacity			   PRESENCE optional	},
	...
} 

SupportedPLMNs-List	::=	SEQUENCE (SIZE (1..maxnoofSPLMNs)) OF SupportedPLMNs-Item 

SupportedPLMNs-Item ::= SEQUENCE {
	pLMN-Identity					PLMN-Identity,
	slice-Support-List				Slice-Support-List												OPTIONAL,
	nR-CGI-Support-List				NR-CGI-Support-List												OPTIONAL,
	qoS-Parameters-Support-List		QoS-Parameters-Support-List										OPTIONAL,
	iE-Extensions					ProtocolExtensionContainer { { SupportedPLMNs-ExtIEs } }		OPTIONAL, 
	...
}

SupportedPLMNs-ExtIEs E1AP-PROTOCOL-EXTENSION ::= {
	...
}







GNB-CU-UP-E1SetupResponse ::= SEQUENCE {
	protocolIEs			ProtocolIE-Container       { {GNB-CU-UP-E1SetupResponseIEs} },
	...
}

GNB-CU-UP-E1SetupResponseIEs
 E1AP-PROTOCOL-IES ::= {
	{ ID id-TransactionID						CRITICALITY reject	TYPE TransactionID					PRESENCE mandatory	}|
	{ ID id-gNB-CU-CP-Name						CRITICALITY ignore	TYPE GNB-CU-CP-Name					PRESENCE optional	},
	...
}







GNB-CU-UP-E1SetupFailure ::= SEQUENCE {
	protocolIEs			ProtocolIE-Container       { {GNB-CU-UP-E1SetupFailureIEs} },
	...
}

GNB-CU-UP-E1SetupFailureIEs E1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}













GNB-CU-CP-E1SetupRequest ::= SEQUENCE {
	protocolIEs			ProtocolIE-Container       { {GNB-CU-CP-E1SetupRequestIEs} },
	...
}

GNB-CU-CP-E1SetupRequestIEs E1AP-PROTOCOL-IES ::= {
	{ ID id-TransactionID						CRITICALITY reject	TYPE TransactionID					PRESENCE mandatory	}|
	{ ID id-gNB-CU-CP-Name						CRITICALITY ignore	TYPE GNB-CU-CP-Name					PRESENCE optional	},
	...
} 







GNB-CU-CP-E1SetupResponse ::= SEQUENCE {
	protocolIEs			ProtocolIE-Container       { {GNB-CU-CP-E1SetupResponseIEs} },
	...
}

GNB-CU-CP-E1SetupResponseIEs
 E1AP-PROTOCOL-IES ::= {
	{ ID id-TransactionID						CRITICALITY reject	TYPE TransactionID					PRESENCE mandatory	}|
	{ ID id-gNB-CU-UP-ID						CRITICALITY reject	TYPE GNB-CU-UP-ID					PRESENCE mandatory	}|
	{ ID id-gNB-CU-UP-Name						CRITICALITY ignore	TYPE GNB-CU-UP-Name					PRESENCE optional	}|
	{ ID id-CNSupport							CRITICALITY reject	TYPE CNSupport						PRESENCE mandatory	}|
	{ ID id-SupportedPLMNs						CRITICALITY reject	TYPE SupportedPLMNs-List			PRESENCE mandatory	}|
	{ ID id-gNB-CU-UP-Capacity					CRITICALITY ignore	TYPE GNB-CU-UP-Capacity			   PRESENCE optional	},
	...
}







GNB-CU-CP-E1SetupFailure ::= SEQUENCE {
	protocolIEs			ProtocolIE-Container       { {GNB-CU-CP-E1SetupFailureIEs} },
	...
}

GNB-CU-CP-E1SetupFailureIEs E1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}













GNB-CU-UP-ConfigurationUpdate ::= SEQUENCE {
	protocolIEs			ProtocolIE-Container       { {GNB-CU-UP-ConfigurationUpdateIEs} },
	...
}

GNB-CU-UP-ConfigurationUpdateIEs E1AP-PROTOCOL-IES ::= {
	{ ID id-TransactionID						CRITICALITY reject	TYPE TransactionID					PRESENCE mandatory	}|
	{ ID id-gNB-CU-UP-ID						CRITICALITY reject	TYPE GNB-CU-UP-ID					PRESENCE mandatory }|
	{ ID id-gNB-CU-UP-Name						CRITICALITY ignore	TYPE GNB-CU-UP-Name					PRESENCE optional	}|
	{ ID id-SupportedPLMNs						CRITICALITY reject	TYPE SupportedPLMNs-List			PRESENCE optional	}|
	{ ID id-gNB-CU-UP-Capacity					CRITICALITY ignore	TYPE GNB-CU-UP-Capacity			   PRESENCE optional	}|
	{ ID id-GNB-CU-UP-TNLA-To-Remove-List		CRITICALITY reject	TYPE GNB-CU-UP-TNLA-To-Remove-List	PRESENCE optional	},
	...
} 

GNB-CU-UP-TNLA-To-Remove-List 	::= SEQUENCE (SIZE(1.. maxnoofTNLAssociations))	OF GNB-CU-UP-TNLA-To-Remove-Item







GNB-CU-UP-ConfigurationUpdateAcknowledge ::= SEQUENCE {
	protocolIEs			ProtocolIE-Container       { {GNB-CU-UP-ConfigurationUpdateAcknowledgeIEs} },
	...
}

GNB-CU-UP-ConfigurationUpdateAcknowledgeIEs
 E1AP-PROTOCOL-IES ::= {
	{ ID id-TransactionID					CRITICALITY reject	TYPE TransactionID						PRESENCE mandatory	}|
	{ ID id-CriticalityDiagnostics			CRITICALITY ignore	TYPE CriticalityDiagnostics				PRESENCE optional	},
	...
}







GNB-CU-UP-ConfigurationUpdateFailure ::= SEQUENCE {
	protocolIEs			ProtocolIE-Container       { {GNB-CU-UP-ConfigurationUpdateFailureIEs} },
	...
}

GNB-CU-UP-ConfigurationUpdateFailureIEs E1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}













GNB-CU-CP-ConfigurationUpdate ::= SEQUENCE {
	protocolIEs			ProtocolIE-Container       { {GNB-CU-CP-ConfigurationUpdateIEs} },
	...
}

GNB-CU-CP-ConfigurationUpdateIEs E1AP-PROTOCOL-IES ::= {
	{ ID id-TransactionID				CRITICALITY reject	TYPE TransactionID				PRESENCE mandatory	}|
	{ ID id-gNB-CU-CP-Name						CRITICALITY ignore	TYPE GNB-CU-UP-Name						PRESENCE optional	}|
	{ ID id-GNB-CU-CP-TNLA-To-Add-List			CRITICALITY ignore	TYPE GNB-CU-CP-TNLA-To-Add-List		PRESENCE optional	}|
	{ ID id-GNB-CU-CP-TNLA-To-Remove-List		CRITICALITY ignore	TYPE GNB-CU-CP-TNLA-To-Remove-List	PRESENCE optional	}|
	{ ID id-GNB-CU-CP-TNLA-To-Update-List		CRITICALITY ignore	TYPE GNB-CU-CP-TNLA-To-Update-List	PRESENCE optional	},
	...
} 

GNB-CU-CP-TNLA-To-Add-List       ::= SEQUENCE (SIZE(1.. maxnoofTNLAssociations))	OF GNB-CU-CP-TNLA-To-Add-Item 
GNB-CU-CP-TNLA-To-Remove-List 	::= SEQUENCE (SIZE(1.. maxnoofTNLAssociations))	OF GNB-CU-CP-TNLA-To-Remove-Item 
GNB-CU-CP-TNLA-To-Update-List		::= SEQUENCE (SIZE(1.. maxnoofTNLAssociations))	OF GNB-CU-CP-TNLA-To-Update-Item







GNB-CU-CP-ConfigurationUpdateAcknowledge ::= SEQUENCE {
	protocolIEs			ProtocolIE-Container       { {GNB-CU-CP-ConfigurationUpdateAcknowledgeIEs} },
	...
}

GNB-CU-CP-ConfigurationUpdateAcknowledgeIEs
 E1AP-PROTOCOL-IES ::= {
	{ ID id-TransactionID						CRITICALITY reject	TYPE TransactionID									PRESENCE mandatory	}|
	{ ID id-CriticalityDiagnostics				CRITICALITY ignore	TYPE CriticalityDiagnostics							PRESENCE optional	}|
	{ ID id-GNB-CU-CP-TNLA-Setup-List			CRITICALITY ignore	TYPE GNB-CU-CP-TNLA-Setup-List					PRESENCE optional	}|
	{ ID id-GNB-CU-CP-TNLA-Failed-To-Setup-List	CRITICALITY ignore	TYPE GNB-CU-CP-TNLA-Failed-To-Setup-List		PRESENCE optional	},
	...
}

GNB-CU-CP-TNLA-Setup-List				::= SEQUENCE (SIZE(1.. maxnoofTNLAssociations))	OF GNB-CU-CP-TNLA-Setup-Item 
GNB-CU-CP-TNLA-Failed-To-Setup-List	::= SEQUENCE (SIZE(1.. maxnoofTNLAssociations))	OF GNB-CU-CP-TNLA-Failed-To-Setup-Item 








GNB-CU-CP-ConfigurationUpdateFailure ::= SEQUENCE {
	protocolIEs			ProtocolIE-Container       { {GNB-CU-CP-ConfigurationUpdateFailureIEs} },
	...
}

GNB-CU-CP-ConfigurationUpdateFailureIEs E1AP-PROTOCOL-IES ::= {
	{ ID id-TransactionID				CRITICALITY reject	TYPE TransactionID				PRESENCE mandatory	}|
	{ ID id-Cause						CRITICALITY ignore	TYPE Cause						PRESENCE mandatory	}|
	{ ID id-TimeToWait					CRITICALITY ignore	TYPE TimeToWait					PRESENCE optional	}|
	{ ID id-CriticalityDiagnostics		CRITICALITY ignore	TYPE CriticalityDiagnostics		PRESENCE optional	},
	...
}













E1ReleaseRequest ::= SEQUENCE {
	protocolIEs			ProtocolIE-Container       { {E1ReleaseRequestIEs} },
	...
}

E1ReleaseRequestIEs E1AP-PROTOCOL-IES ::= { 
	{ ID id-TransactionID				CRITICALITY reject	TYPE TransactionID				PRESENCE mandatory	}|
	{ ID id-Cause						CRITICALITY ignore	TYPE Cause						PRESENCE mandatory	},
	...
}







E1ReleaseResponse ::= SEQUENCE {
	protocolIEs			ProtocolIE-Container       { {E1ReleaseResponseIEs} },
	...
}

E1ReleaseResponseIEs E1AP-PROTOCOL-IES ::= {
	{ ID id-TransactionID				CRITICALITY reject	TYPE TransactionID				PRESENCE mandatory	},
	...
}













BearerContextSetupRequest ::= SEQUENCE {
	protocolIEs			ProtocolIE-Container       { { BearerContextSetupRequestIEs} },
	...
}

BearerContextSetupRequestIEs E1AP-PROTOCOL-IES ::= {
	{ ID id-gNB-CU-CP-UE-E1AP-ID				CRITICALITY reject	TYPE GNB-CU-CP-UE-E1AP-ID							PRESENCE mandatory }|
	{ ID id-SecurityInformation					CRITICALITY reject	TYPE SecurityInformation							PRESENCE mandatory }|
	{ ID id-UEDLAggregateMaximumBitRate			CRITICALITY reject	TYPE BitRate										PRESENCE mandatory }|
	{ ID id-UEDLMaximumIntegrityProtectedDataRate	CRITICALITY reject		TYPE BitRate								PRESENCE optional	 }|
	{ ID id-Serving-PLMN						CRITICALITY ignore	TYPE PLMN-Identity									PRESENCE mandatory }|
	{ ID id-ActivityNotificationLevel			CRITICALITY reject	TYPE ActivityNotificationLevel					PRESENCE mandatory }|
	{ ID id-UE-Inactivity-Timer					CRITICALITY reject	TYPE Inactivity-Timer								PRESENCE optional  }|
	{ ID id-BearerContextStatusChange			CRITICALITY reject	TYPE BearerContextStatusChange					PRESENCE optional  }|
	{ ID id-System-BearerContextSetupRequest	CRITICALITY reject	TYPE System-BearerContextSetupRequest				PRESENCE mandatory }|
	{ ID id-RANUEID								CRITICALITY ignore	TYPE RANUEID										PRESENCE optional }|
	{ ID id-GNB-DU-ID							CRITICALITY ignore	TYPE GNB-DU-ID										PRESENCE optional },
	...
} 

System-BearerContextSetupRequest	::=	CHOICE {
	e-UTRAN-BearerContextSetupRequest		ProtocolIE-Container		 	{{EUTRAN-BearerContextSetupRequest}},
	nG-RAN-BearerContextSetupRequest		ProtocolIE-Container		 	{{NG-RAN-BearerContextSetupRequest}},
	choice-extension						ProtocolIE-SingleContainer		{{System-BearerContextSetupRequest-ExtIEs}}
}

System-BearerContextSetupRequest-ExtIEs E1AP-PROTOCOL-IES::= {
	...
}


EUTRAN-BearerContextSetupRequest E1AP-PROTOCOL-IES ::= {
	{ ID id-DRB-To-Setup-List-EUTRAN		CRITICALITY reject	 TYPE DRB-To-Setup-List-EUTRAN		PRESENCE mandatory },
	...
}

NG-RAN-BearerContextSetupRequest E1AP-PROTOCOL-IES ::= {
	{ ID id-PDU-Session-Resource-To-Setup-List		CRITICALITY reject	 TYPE PDU-Session-Resource-To-Setup-List		PRESENCE mandatory },
	...
}








BearerContextSetupResponse ::= SEQUENCE {
	protocolIEs			ProtocolIE-Container       { { BearerContextSetupResponseIEs} },
	...
}


BearerContextSetupResponseIEs E1AP-PROTOCOL-IES ::= {
	{ ID id-gNB-CU-CP-UE-E1AP-ID				CRITICALITY reject	TYPE GNB-CU-CP-UE-E1AP-ID							PRESENCE mandatory	}|
	{ ID id-gNB-CU-UP-UE-E1AP-ID				CRITICALITY reject	TYPE GNB-CU-UP-UE-E1AP-ID							PRESENCE mandatory	}|
	{ ID id-System-BearerContextSetupResponse	CRITICALITY ignore	TYPE System-BearerContextSetupResponse				PRESENCE mandatory  },
	...
}

System-BearerContextSetupResponse::=	CHOICE {
	e-UTRAN-BearerContextSetupResponse		ProtocolIE-Container 			{{EUTRAN-BearerContextSetupResponse}},
	nG-RAN-BearerContextSetupResponse		ProtocolIE-Container 			{{NG-RAN-BearerContextSetupResponse}},
	choice-extension						ProtocolIE-SingleContainer		{{System-BearerContextSetupResponse-ExtIEs}}
}

System-BearerContextSetupResponse-ExtIEs E1AP-PROTOCOL-IES ::= {
	...
}

EUTRAN-BearerContextSetupResponse E1AP-PROTOCOL-IES ::= {
	{ ID id-DRB-Setup-List-EUTRAN 		CRITICALITY ignore	 TYPE DRB-Setup-List-EUTRAN			PRESENCE mandatory }|
	{ ID id-DRB-Failed-List-EUTRAN 		CRITICALITY ignore	 TYPE DRB-Failed-List-EUTRAN		PRESENCE optional  },
	...
}

NG-RAN-BearerContextSetupResponse E1AP-PROTOCOL-IES ::= {
	{ ID id-PDU-Session-Resource-Setup-List 	CRITICALITY ignore	 TYPE PDU-Session-Resource-Setup-List		PRESENCE mandatory }|
	{ ID id-PDU-Session-Resource-Failed-List 	CRITICALITY ignore	 TYPE PDU-Session-Resource-Failed-List		PRESENCE optional  },
	...
}








BearerContextSetupFailure ::= SEQUENCE {
	protocolIEs			ProtocolIE-Container       { { BearerContextSetupFailureIEs} },
	...
}

BearerContextSetupFailureIEs E1AP-PROTOCOL-IES ::= {
	{ ID id-gNB-CU-CP-UE-E1AP-ID		CRITICALITY reject	TYPE GNB-CU-CP-UE-E1AP-ID			PRESENCE mandatory	}|
	{ ID id-gNB-CU-UP-UE-E1AP-ID		CRITICALITY ignore	TYPE GNB-CU-UP-UE-E1AP-ID			PRESENCE optional	}|
	{ ID id-Cause						CRITICALITY ignore	TYPE Cause							PRESENCE mandatory	}|
	{ ID id-CriticalityDiagnostics		CRITICALITY ignore	TYPE CriticalityDiagnostics			PRESENCE optional	},
	...
}













BearerContextModificationRequest ::= SEQUENCE {
	protocolIEs			ProtocolIE-Container       { { BearerContextModificationRequestIEs} },
	...
}

BearerContextModificationRequestIEs E1AP-PROTOCOL-IES ::= {
	{ ID id-gNB-CU-CP-UE-E1AP-ID					CRITICALITY reject	TYPE GNB-CU-CP-UE-E1AP-ID									PRESENCE mandatory }|
	{ ID id-gNB-CU-UP-UE-E1AP-ID					CRITICALITY reject	TYPE GNB-CU-UP-UE-E1AP-ID									PRESENCE mandatory }|
	{ ID id-SecurityInformation						CRITICALITY reject	TYPE SecurityInformation									PRESENCE optional  }|
	{ ID id-UEDLAggregateMaximumBitRate				CRITICALITY reject	TYPE BitRate												PRESENCE optional  }|
	{ ID id-UEDLMaximumIntegrityProtectedDataRate		CRITICALITY reject	TYPE BitRate											PRESENCE optional	 }|
	{ ID id-BearerContextStatusChange				CRITICALITY reject	TYPE BearerContextStatusChange							PRESENCE optional  }|
	{ ID id-New-UL-TNL-Information-Required			CRITICALITY reject	TYPE New-UL-TNL-Information-Required					PRESENCE optional  }|
	{ ID id-UE-Inactivity-Timer						CRITICALITY reject	TYPE Inactivity-Timer										PRESENCE optional  }|
	{ ID id-DataDiscardRequired					CRITICALITY ignore	TYPE DataDiscardRequired											PRESENCE optional  }|
	{ ID id-System-BearerContextModificationRequest	CRITICALITY reject	TYPE System-BearerContextModificationRequest		PRESENCE optional  }|
	{ ID id-RANUEID										CRITICALITY ignore	TYPE RANUEID												PRESENCE optional }|
	{ ID id-GNB-DU-ID									CRITICALITY ignore	TYPE GNB-DU-ID												PRESENCE optional }|
	{ ID id-ActivityNotificationLevel					CRITICALITY ignore	TYPE ActivityNotificationLevel							PRESENCE optional },
	...
} 

System-BearerContextModificationRequest	::=	CHOICE {
	e-UTRAN-BearerContextModificationRequest		ProtocolIE-Container 			{{EUTRAN-BearerContextModificationRequest}},
	nG-RAN-BearerContextModificationRequest			ProtocolIE-Container 			{{NG-RAN-BearerContextModificationRequest}},
	choice-extension								ProtocolIE-SingleContainer		{{System-BearerContextModificationRequest-ExtIEs}}
}

System-BearerContextModificationRequest-ExtIEs E1AP-PROTOCOL-IES ::= {
	...
}

EUTRAN-BearerContextModificationRequest E1AP-PROTOCOL-IES ::= {
	{ ID id-DRB-To-Setup-Mod-List-EUTRAN		CRITICALITY reject	 TYPE DRB-To-Setup-Mod-List-EUTRAN		PRESENCE optional }|
	{ ID id-DRB-To-Modify-List-EUTRAN			CRITICALITY reject	 TYPE DRB-To-Modify-List-EUTRAN			PRESENCE optional }|
	{ ID id-DRB-To-Remove-List-EUTRAN			CRITICALITY reject	 TYPE DRB-To-Remove-List-EUTRAN			PRESENCE optional },
	...
}

NG-RAN-BearerContextModificationRequest E1AP-PROTOCOL-IES ::= {
	{ ID id-PDU-Session-Resource-To-Setup-Mod-List	CRITICALITY reject	 TYPE PDU-Session-Resource-To-Setup-Mod-List	PRESENCE optional }|
	{ ID id-PDU-Session-Resource-To-Modify-List 	CRITICALITY reject	 TYPE PDU-Session-Resource-To-Modify-List		PRESENCE optional }|
	{ ID id-PDU-Session-Resource-To-Remove-List		CRITICALITY reject	 TYPE PDU-Session-Resource-To-Remove-List		PRESENCE optional },
	...
}








BearerContextModificationResponse ::= SEQUENCE {
	protocolIEs			ProtocolIE-Container       { { BearerContextModificationResponseIEs} },
	...
}


BearerContextModificationResponseIEs E1AP-PROTOCOL-IES ::= {
	{ ID id-gNB-CU-CP-UE-E1AP-ID						CRITICALITY reject	TYPE GNB-CU-CP-UE-E1AP-ID								PRESENCE mandatory }|
	{ ID id-gNB-CU-UP-UE-E1AP-ID						CRITICALITY reject	TYPE GNB-CU-UP-UE-E1AP-ID								PRESENCE mandatory }|
	{ ID id-System-BearerContextModificationResponse	CRITICALITY ignore	TYPE System-BearerContextModificationResponse		PRESENCE optional  },
	...
}

System-BearerContextModificationResponse	::=	CHOICE {
	e-UTRAN-BearerContextModificationResponse			ProtocolIE-Container {{EUTRAN-BearerContextModificationResponse}},
	nG-RAN-BearerContextModificationResponse			ProtocolIE-Container {{NG-RAN-BearerContextModificationResponse}},
	choice-extension									ProtocolIE-SingleContainer {{System-BearerContextModificationResponse-ExtIEs}}
}

System-BearerContextModificationResponse-ExtIEs E1AP-PROTOCOL-IES ::= {
	...
}

EUTRAN-BearerContextModificationResponse E1AP-PROTOCOL-IES ::= {
	{ ID id-DRB-Setup-Mod-List-EUTRAN				CRITICALITY ignore	TYPE DRB-Setup-Mod-List-EUTRAN					PRESENCE optional }|
	{ ID id-DRB-Failed-Mod-List-EUTRAN				CRITICALITY ignore	TYPE DRB-Failed-Mod-List-EUTRAN				PRESENCE optional }|
	{ ID id-DRB-Modified-List-EUTRAN				CRITICALITY ignore	TYPE DRB-Modified-List-EUTRAN					PRESENCE optional }|
	{ ID id-DRB-Failed-To-Modify-List-EUTRAN		CRITICALITY ignore	TYPE DRB-Failed-To-Modify-List-EUTRAN		PRESENCE optional },
	...
}

NG-RAN-BearerContextModificationResponse E1AP-PROTOCOL-IES ::= {
	{ ID id-PDU-Session-Resource-Setup-Mod-List 		CRITICALITY reject	TYPE PDU-Session-Resource-Setup-Mod-List				PRESENCE optional }|
	{ ID id-PDU-Session-Resource-Failed-Mod-List		CRITICALITY reject	TYPE PDU-Session-Resource-Failed-Mod-List				PRESENCE optional }|
	{ ID id-PDU-Session-Resource-Modified-List			CRITICALITY reject	TYPE PDU-Session-Resource-Modified-List				PRESENCE optional }|
	{ ID id-PDU-Session-Resource-Failed-To-Modify-List	CRITICALITY reject	TYPE PDU-Session-Resource-Failed-To-Modify-List		PRESENCE optional },
	...
}








BearerContextModificationFailure ::= SEQUENCE {
	protocolIEs			ProtocolIE-Container       { { BearerContextModificationFailureIEs} },
	...
}

BearerContextModificationFailureIEs E1AP-PROTOCOL-IES ::= {
	{ ID id-gNB-CU-CP-UE-E1AP-ID		CRITICALITY reject	TYPE GNB-CU-CP-UE-E1AP-ID			PRESENCE mandatory	}|
	{ ID id-gNB-CU-UP-UE-E1AP-ID		CRITICALITY reject	TYPE GNB-CU-UP-UE-E1AP-ID			PRESENCE mandatory	}|
	{ ID id-Cause						CRITICALITY ignore	TYPE Cause							PRESENCE mandatory	}|
	{ ID id-CriticalityDiagnostics		CRITICALITY ignore	TYPE CriticalityDiagnostics			PRESENCE optional	},
	...
}













BearerContextModificationRequired ::= SEQUENCE {
	protocolIEs			ProtocolIE-Container       { { BearerContextModificationRequiredIEs} },
	...
}

BearerContextModificationRequiredIEs E1AP-PROTOCOL-IES ::= {
	{ ID id-gNB-CU-CP-UE-E1AP-ID						CRITICALITY reject	TYPE GNB-CU-CP-UE-E1AP-ID									PRESENCE mandatory }|
	{ ID id-gNB-CU-UP-UE-E1AP-ID						CRITICALITY reject	TYPE GNB-CU-UP-UE-E1AP-ID									PRESENCE mandatory }|
	{ ID id-System-BearerContextModificationRequired	CRITICALITY reject	TYPE System-BearerContextModificationRequired			PRESENCE mandatory },	
	...
} 

System-BearerContextModificationRequired	::=	CHOICE {
	e-UTRAN-BearerContextModificationRequired		ProtocolIE-Container {{EUTRAN-BearerContextModificationRequired}},
	nG-RAN-BearerContextModificationRequired		ProtocolIE-Container {{NG-RAN-BearerContextModificationRequired}},
	choice-extension								ProtocolIE-SingleContainer {{System-BearerContextModificationRequired-ExtIEs}}
}

System-BearerContextModificationRequired-ExtIEs E1AP-PROTOCOL-IES ::= {
	...
}

EUTRAN-BearerContextModificationRequired E1AP-PROTOCOL-IES ::= {
	{ ID id-DRB-Required-To-Modify-List-EUTRAN	CRITICALITY reject	TYPE DRB-Required-To-Modify-List-EUTRAN	PRESENCE optional }|
	{ ID id-DRB-Required-To-Remove-List-EUTRAN	CRITICALITY reject	TYPE DRB-Required-To-Remove-List-EUTRAN	PRESENCE optional },
	...
}

NG-RAN-BearerContextModificationRequired E1AP-PROTOCOL-IES ::= {
	{ ID id-PDU-Session-Resource-Required-To-Modify-List	CRITICALITY reject	TYPE PDU-Session-Resource-Required-To-Modify-List	PRESENCE optional }|
	{ ID id-PDU-Session-Resource-To-Remove-List	CRITICALITY reject	 TYPE PDU-Session-Resource-To-Remove-List	PRESENCE optional },
	...
}








BearerContextModificationConfirm ::= SEQUENCE {
	protocolIEs			ProtocolIE-Container       { { BearerContextModificationConfirmIEs} },
	...
}


BearerContextModificationConfirmIEs E1AP-PROTOCOL-IES ::= {
	{ ID id-gNB-CU-CP-UE-E1AP-ID						CRITICALITY reject	TYPE GNB-CU-CP-UE-E1AP-ID							PRESENCE mandatory }|
	{ ID id-gNB-CU-UP-UE-E1AP-ID						CRITICALITY reject	TYPE GNB-CU-UP-UE-E1AP-ID							PRESENCE mandatory }|
	{ ID id-System-BearerContextModificationConfirm		CRITICALITY ignore	TYPE System-BearerContextModificationConfirm		PRESENCE optional  },
	...
}

System-BearerContextModificationConfirm	::=	CHOICE {
	e-UTRAN-BearerContextModificationConfirm		ProtocolIE-Container {{EUTRAN-BearerContextModificationConfirm}},
	nG-RAN-BearerContextModificationConfirm			ProtocolIE-Container {{NG-RAN-BearerContextModificationConfirm}},
	choice-extension								ProtocolIE-SingleContainer {{System-BearerContextModificationConfirm-ExtIEs}}
}

System-BearerContextModificationConfirm-ExtIEs E1AP-PROTOCOL-IES ::= {
	...
}

EUTRAN-BearerContextModificationConfirm E1AP-PROTOCOL-IES ::= {
	{ ID id-DRB-Confirm-Modified-List-EUTRAN	CRITICALITY ignore	 TYPE DRB-Confirm-Modified-List-EUTRAN	PRESENCE optional },
	...
}

NG-RAN-BearerContextModificationConfirm E1AP-PROTOCOL-IES ::= {
	{ ID id-PDU-Session-Resource-Confirm-Modified-List	CRITICALITY ignore	 TYPE PDU-Session-Resource-Confirm-Modified-List	PRESENCE optional },
	...
}














BearerContextReleaseCommand ::= SEQUENCE {
	protocolIEs			ProtocolIE-Container       { { BearerContextReleaseCommandIEs} },
	...
}

BearerContextReleaseCommandIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-Cause							CRITICALITY ignore	TYPE Cause							PRESENCE mandatory },	
	...
} 







BearerContextReleaseComplete ::= SEQUENCE {
	protocolIEs			ProtocolIE-Container       { { BearerContextReleaseCompleteIEs} },
	...
}


BearerContextReleaseCompleteIEs E1AP-PROTOCOL-IES ::= {
	{ ID id-gNB-CU-CP-UE-E1AP-ID		CRITICALITY reject	TYPE GNB-CU-CP-UE-E1AP-ID			PRESENCE mandatory }|
	{ ID id-gNB-CU-UP-UE-E1AP-ID		CRITICALITY reject	TYPE GNB-CU-UP-UE-E1AP-ID			PRESENCE mandatory }|
	{ ID id-CriticalityDiagnostics		CRITICALITY ignore	TYPE CriticalityDiagnostics			PRESENCE optional	},
	...
}













BearerContextReleaseRequest ::= SEQUENCE {
	protocolIEs			ProtocolIE-Container       { { BearerContextReleaseRequestIEs} },
	...
}

BearerContextReleaseRequestIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-DRB-Status-List					CRITICALITY ignore	TYPE DRB-Status-List				PRESENCE optional  }|
	{ ID id-Cause							CRITICALITY ignore	TYPE Cause							PRESENCE mandatory },	
	...
} 

DRB-Status-List ::= SEQUENCE (SIZE(1..maxnoofDRBs)) OF DRB-Status-Item














BearerContextInactivityNotification ::= SEQUENCE {
	protocolIEs			ProtocolIE-Container       { { BearerContextInactivityNotificationIEs } },
	...
}

BearerContextInactivityNotificationIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-ActivityInformation				CRITICALITY reject	TYPE ActivityInformation			PRESENCE mandatory },
	...
} 














DLDataNotification ::= SEQUENCE {
	protocolIEs			ProtocolIE-Container       { { DLDataNotificationIEs } },
	...
}

DLDataNotificationIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-PPI							CRITICALITY ignore	TYPE PPI							PRESENCE optional },
	...
} 









ULDataNotification ::= SEQUENCE {
	protocolIEs			ProtocolIE-Container       { { ULDataNotificationIEs } },
	...
}

ULDataNotificationIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-PDU-Session-To-Notify-List		CRITICALITY reject	 TYPE PDU-Session-To-Notify-List	PRESENCE mandatory },
	...
}













DataUsageReport ::= SEQUENCE {
	protocolIEs			ProtocolIE-Container       { { DataUsageReportIEs } },
	...
}

DataUsageReportIEs E1AP-PROTOCOL-IES ::= {
	{ ID id-gNB-CU-CP-UE-E1AP-ID			CRITICALITY reject	TYPE GNB-CU-CP-UE-E1AP-ID			PRESENCE mandatory }|
	{ ID id-gNB-CU-UP-UE-E1AP-ID			CRITICALITY reject	TYPE GNB-CU-UP-UE-E1AP-ID			PRESENCE mandatory }|
	{ ID id-Data-Usage-Report-List			CRITICALITY ignore	TYPE Data-Usage-Report-List			PRESENCE mandatory },	
	...
}














GNB-CU-UP-CounterCheckRequest ::= SEQUENCE {
	protocolIEs			ProtocolIE-Container       { { GNB-CU-UP-CounterCheckRequestIEs } },
	...
}

GNB-CU-UP-CounterCheckRequestIEs E1AP-PROTOCOL-IES ::= {
	{ ID id-gNB-CU-CP-UE-E1AP-ID					CRITICALITY reject	TYPE GNB-CU-CP-UE-E1AP-ID							PRESENCE mandatory }|
	{ ID id-gNB-CU-UP-UE-E1AP-ID					CRITICALITY reject	TYPE GNB-CU-UP-UE-E1AP-ID							PRESENCE mandatory }|
	{ ID id-System-GNB-CU-UP-CounterCheckRequest	CRITICALITY reject	TYPE System-GNB-CU-UP-CounterCheckRequest	PRESENCE mandatory },
	...
} 

System-GNB-CU-UP-CounterCheckRequest	::=	CHOICE {
	e-UTRAN-GNB-CU-UP-CounterCheckRequest		ProtocolIE-Container		{{EUTRAN-GNB-CU-UP-CounterCheckRequest}},
	nG-RAN-GNB-CU-UP-CounterCheckRequest		ProtocolIE-Container		{{NG-RAN-GNB-CU-UP-CounterCheckRequest}},
	choice-extension							ProtocolIE-SingleContainer	{{System-GNB-CU-UP-CounterCheckRequest-ExtIEs}}
}

System-GNB-CU-UP-CounterCheckRequest-ExtIEs E1AP-PROTOCOL-IES::= {
	...
}

EUTRAN-GNB-CU-UP-CounterCheckRequest E1AP-PROTOCOL-IES ::= {
	{ ID id-DRBs-Subject-To-Counter-Check-List-EUTRAN	CRITICALITY ignore	 TYPE DRBs-Subject-To-Counter-Check-List-EUTRAN	PRESENCE mandatory },
	...
}

NG-RAN-GNB-CU-UP-CounterCheckRequest E1AP-PROTOCOL-IES ::= {
	{ ID id-DRBs-Subject-To-Counter-Check-List-NG-RAN	CRITICALITY ignore	 TYPE DRBs-Subject-To-Counter-Check-List-NG-RAN	PRESENCE mandatory },
	...
}















GNB-CU-UP-StatusIndication ::= SEQUENCE {
	protocolIEs			ProtocolIE-Container       { { GNB-CU-UP-StatusIndicationIEs} },
	...
}


GNB-CU-UP-StatusIndicationIEs E1AP-PROTOCOL-IES ::= { 
	{ ID id-TransactionID						CRITICALITY reject	TYPE TransactionID				 			PRESENCE mandatory	}|
	{ ID id-GNB-CU-UP-OverloadInformation	CRITICALITY reject	TYPE GNB-CU-UP-OverloadInformation		PRESENCE mandatory	},
	...
}







MRDC-DataUsageReport ::= SEQUENCE {
	protocolIEs		ProtocolIE-Container		{ { MRDC-DataUsageReportIEs } },
	...
}

MRDC-DataUsageReportIEs E1AP-PROTOCOL-IES ::= {
	{ ID id-gNB-CU-CP-UE-E1AP-ID					CRITICALITY reject		TYPE GNB-CU-CP-UE-E1AP-ID							PRESENCE mandatory}|
	{ ID id-gNB-CU-UP-UE-E1AP-ID					CRITICALITY reject		TYPE GNB-CU-UP-UE-E1AP-ID							PRESENCE mandatory}|
	{ ID id-PDU-Session-Resource-Data-Usage-List	CRITICALITY ignore		TYPE PDU-Session-Resource-Data-Usage-List	PRESENCE mandatory},
	...
}








PrivateMessage ::= SEQUENCE {
	privateIEs		PrivateIE-Container	{{PrivateMessage-IEs}},
	...
}

PrivateMessage-IEs E1AP-PRIVATE-IES ::= {
	...
}

END







E1AP-IEs {
itu-t (0) identified-organization (4) etsi (0) mobileDomain (0)
ngran-access (22) modules (3) e1ap (5) version1 (1) e1ap-IEs (2) }

DEFINITIONS AUTOMATIC TAGS ::= 

BEGIN

IMPORTS	
	
	id-CommonNetworkInstance,
	id-SNSSAI,
	id-OldQoSFlowMap-ULendmarkerexpected,
	id-DRB-QoS,
	id-endpoint-IP-Address-and-Port,
	id-NetworkInstance,
	id-QoSFlowMappingIndication,
	id-TNLAssociationTransportLayerAddressgNBCUUP,
	id-Cause,
	maxnoofErrors,
	maxnoofSliceItems,
	maxnoofEUTRANQOSParameters,
	maxnoofNGRANQOSParameters,
	maxnoofDRBs,
	maxnoofPDUSessionResource,
	maxnoofQoSFlows,
	maxnoofUPParameters,
	maxnoofCellGroups,
	maxnooftimeperiods,
	maxnoofNRCGI

FROM E1AP-Constants

	Criticality,
	ProcedureCode,
	ProtocolIE-ID,
	TriggeringMessage

FROM E1AP-CommonDataTypes

	ProtocolExtensionContainer{},
	ProtocolIE-SingleContainer{},	
	E1AP-PROTOCOL-EXTENSION,
	E1AP-PROTOCOL-IES


FROM E1AP-Containers;



ActivityInformation	::=	CHOICE	{
	dRB-Activity-List						DRB-Activity-List,
	pDU-Session-Resource-Activity-List		PDU-Session-Resource-Activity-List,
	uE-Activity								UE-Activity, 
	choice-extension						ProtocolIE-SingleContainer	{{ActivityInformation-ExtIEs}}
}

ActivityInformation-ExtIEs E1AP-PROTOCOL-IES ::= {
	...
}

ActivityNotificationLevel	::=	ENUMERATED	{
	drb,
	pdu-session,
	ue,
	...
}

AveragingWindow  ::= INTEGER (0..4095, ...) 



BearerContextStatusChange	::= 	ENUMERATED {
	suspend,
	resume,
	...
}

BitRate ::= INTEGER (0..4000000000000, ...)



Cause ::= CHOICE {
	radioNetwork		CauseRadioNetwork,
	transport			CauseTransport,
	protocol			CauseProtocol,
	misc				CauseMisc,
	choice-extension	ProtocolIE-SingleContainer	{{Cause-ExtIEs}}
}

Cause-ExtIEs E1AP-PROTOCOL-IES ::= {
	...
}

CauseMisc ::= ENUMERATED {
	control-processing-overload,
	not-enough-user-plane-processing-resources,
	hardware-failure,
	om-intervention,
	unspecified,
	...
}

CauseProtocol ::= ENUMERATED {
	transfer-syntax-error,
	abstract-syntax-error-reject,
	abstract-syntax-error-ignore-and-notify,
	message-not-compatible-with-receiver-state,
	semantic-error,
	abstract-syntax-error-falsely-constructed-message,
	unspecified,
	...
}

CauseRadioNetwork ::= ENUMERATED {
	unspecified,
	unknown-or-already-allocated-gnb-cu-cp-ue-e1ap-id,
	unknown-or-already-allocated-gnb-cu-up-ue-e1ap-id,
	unknown-or-inconsistent-pair-of-ue-e1ap-id,
	interaction-with-other-procedure,
	pPDCP-Count-wrap-around,
	not-supported-QCI-value,
	not-supported-5QI-value,
	encryption-algorithms-not-supported, 
	integrity-protection-algorithms-not-supported,
	uP-integrity-protection-not-possible, 
	uP-confidentiality-protection-not-possible,
	multiple-PDU-Session-ID-Instances,
	unknown-PDU-Session-ID,
	multiple-QoS-Flow-ID-Instances,
	unknown-QoS-Flow-ID,
	multiple-DRB-ID-Instances,
	unknown-DRB-ID,
	invalid-QoS-combination,
	procedure-cancelled,
	normal-release,
	no-radio-resources-available,
	action-desirable-for-radio-reasons,
	resources-not-available-for-the-slice,
	pDCP-configuration-not-supported,
	...,
	ue-dl-max-IP-data-rate-reason,
	uP-integrity-protection-failure,
	release-due-to-pre-emption
}

CauseTransport ::= ENUMERATED {
	unspecified,
	transport-resource-unavailable,
	...
}

Cell-Group-Information	::= SEQUENCE (SIZE(1.. maxnoofCellGroups)) OF Cell-Group-Information-Item

Cell-Group-Information-Item	::=	SEQUENCE {
	cell-Group-ID							Cell-Group-ID,
	uL-Configuration						UL-Configuration		OPTIONAL,
	dL-TX-Stop								DL-TX-Stop				OPTIONAL,
	rAT-Type								RAT-Type				OPTIONAL,
	iE-Extensions							ProtocolExtensionContainer { { Cell-Group-Information-Item-ExtIEs } }	OPTIONAL,
	...
}

Cell-Group-Information-Item-ExtIEs		E1AP-PROTOCOL-EXTENSION ::= {
	...
}


Cell-Group-ID	::=		INTEGER (0..3, ...)

CipheringAlgorithm	::=	ENUMERATED {
	nEA0,
	c-128-NEA1,
	c-128-NEA2,
	c-128-NEA3,
	...
}

CNSupport ::= ENUMERATED {
	c-epc,
	c-5gc,
	both,
	...
}

CommonNetworkInstance ::= OCTET STRING

ConfidentialityProtectionIndication ::= ENUMERATED {
	required,
	preferred,
	not-needed,
	...
}


ConfidentialityProtectionResult ::= ENUMERATED {
	performed,
	not-performed,
	...
}


CP-TNL-Information		::= 	CHOICE {
	endpoint-IP-Address		TransportLayerAddress, 
	choice-extension		ProtocolIE-SingleContainer	{{CP-TNL-Information-ExtIEs}}
}

CP-TNL-Information-ExtIEs E1AP-PROTOCOL-IES ::= {
	{ ID id-endpoint-IP-Address-and-Port	CRITICALITY reject	TYPE Endpoint-IP-address-and-port 	PRESENCE mandatory},
	...
}


CriticalityDiagnostics ::= SEQUENCE {
	procedureCode					ProcedureCode					OPTIONAL,
	triggeringMessage				TriggeringMessage				OPTIONAL,
	procedureCriticality			Criticality						OPTIONAL,
	transactionID					TransactionID					OPTIONAL,
	iEsCriticalityDiagnostics		CriticalityDiagnostics-IE-List	OPTIONAL,
	iE-Extensions					ProtocolExtensionContainer { {CriticalityDiagnostics-ExtIEs} }	OPTIONAL,
	...
}


CriticalityDiagnostics-ExtIEs E1AP-PROTOCOL-EXTENSION ::= {
	...
}

CriticalityDiagnostics-IE-List ::= SEQUENCE (SIZE (1..maxnoofErrors)) OF
	SEQUENCE {
		iECriticality			Criticality,
		iE-ID					ProtocolIE-ID,
		typeOfError				TypeOfError,
		iE-Extensions			ProtocolExtensionContainer { {CriticalityDiagnostics-IE-List-ExtIEs} } OPTIONAL,
		...
}

CriticalityDiagnostics-IE-List-ExtIEs E1AP-PROTOCOL-EXTENSION ::= {
	...
}



Data-Forwarding-Information-Request	::=	SEQUENCE {
	data-Forwarding-Request					Data-Forwarding-Request,
	qoS-Flows-Forwarded-On-Fwd-Tunnels	QoS-Flow-Mapping-List			OPTIONAL,
	iE-Extensions							ProtocolExtensionContainer { { Data-Forwarding-Information-Request-ExtIEs } }	OPTIONAL,
	...
}

Data-Forwarding-Information-Request-ExtIEs		E1AP-PROTOCOL-EXTENSION ::= {
	...
}

Data-Forwarding-Information	::=	SEQUENCE {
	uL-Data-Forwarding						UP-TNL-Information		OPTIONAL,
	dL-Data-Forwarding						UP-TNL-Information		OPTIONAL,
	iE-Extensions							ProtocolExtensionContainer { { Data-Forwarding-Information-ExtIEs } }	OPTIONAL,
	...
}

Data-Forwarding-Information-ExtIEs		E1AP-PROTOCOL-EXTENSION ::= {
	...
}

Data-Forwarding-Request ::= ENUMERATED	{
	uL,
	dL,
	both,
	...
}

Data-Usage-per-PDU-Session-Report ::= SEQUENCE {
	secondaryRATType			ENUMERATED {nR, e-UTRA, ...},
	pDU-session-Timed-Report-List			SEQUENCE (SIZE(1..maxnooftimeperiods)) OF MRDC-Data-Usage-Report-Item,
	iE-Extensions				ProtocolExtensionContainer { { Data-Usage-per-PDU-Session-Report-ExtIEs} } OPTIONAL,
...
}

Data-Usage-per-PDU-Session-Report-ExtIEs E1AP-PROTOCOL-EXTENSION ::= {
	...
}

Data-Usage-per-QoS-Flow-List	::= SEQUENCE (SIZE(1..maxnoofQoSFlows)) OF Data-Usage-per-QoS-Flow-Item

Data-Usage-per-QoS-Flow-Item ::= SEQUENCE {
	qoS-Flow-Identifier		QoS-Flow-Identifier,
	secondaryRATType			ENUMERATED {nR, e-UTRA, ...},
	qoS-Flow-Timed-Report-List			SEQUENCE (SIZE(1..maxnooftimeperiods)) OF MRDC-Data-Usage-Report-Item,
	iE-Extensions				ProtocolExtensionContainer { { Data-Usage-per-QoS-Flow-Item-ExtIEs} } OPTIONAL,
...
}

Data-Usage-per-QoS-Flow-Item-ExtIEs E1AP-PROTOCOL-EXTENSION ::= {
	...
}

Data-Usage-Report-List	::= SEQUENCE (SIZE(1.. maxnoofDRBs)) OF Data-Usage-Report-Item

Data-Usage-Report-Item	::= SEQUENCE {
	dRB-ID						DRB-ID,
	rAT-Type					RAT-Type,
	dRB-Usage-Report-List		DRB-Usage-Report-List,
	iE-Extensions	ProtocolExtensionContainer { { Data-Usage-Report-ItemExtIEs } }	OPTIONAL,
	...
}

Data-Usage-Report-ItemExtIEs 	E1AP-PROTOCOL-EXTENSION ::= {
	...
}

DefaultDRB	::=	ENUMERATED	{
	true,
	false,
	...
}

DiscardTimer	::=	ENUMERATED {ms10, ms20, ms30, ms40, ms50, ms60, ms75, ms100, ms150, ms200, ms250, ms300, ms500, ms750, ms1500, infinity}

DL-TX-Stop	::=	ENUMERATED	{
	stop,
	resume,
	...
}

DRB-Activity	::= ENUMERATED {
	active,
	not-active,
	...
}

DRB-Activity-List ::= SEQUENCE (SIZE(1..maxnoofDRBs)) OF DRB-Activity-Item

DRB-Activity-Item	::= SEQUENCE {
	dRB-ID						DRB-ID,
	dRB-Activity				DRB-Activity,
	iE-Extensions	ProtocolExtensionContainer { { DRB-Activity-ItemExtIEs } }	OPTIONAL,
	...
}

DRB-Activity-ItemExtIEs 	E1AP-PROTOCOL-EXTENSION ::= {
	...
}

DRB-Confirm-Modified-List-EUTRAN	::= SEQUENCE (SIZE(1.. maxnoofDRBs)) OF DRB-Confirm-Modified-Item-EUTRAN

DRB-Confirm-Modified-Item-EUTRAN	::=	SEQUENCE {
	dRB-ID									DRB-ID,
	cell-Group-Information					Cell-Group-Information	OPTIONAL,
	iE-Extensions							ProtocolExtensionContainer { { DRB-Confirm-Modified-Item-EUTRAN-ExtIEs } }	OPTIONAL,
	...
}

DRB-Confirm-Modified-Item-EUTRAN-ExtIEs		E1AP-PROTOCOL-EXTENSION ::= {
	...
}

DRB-Confirm-Modified-List-NG-RAN	::= SEQUENCE (SIZE(1.. maxnoofDRBs)) OF DRB-Confirm-Modified-Item-NG-RAN

DRB-Confirm-Modified-Item-NG-RAN	::=	SEQUENCE {
	dRB-ID									DRB-ID,
	cell-Group-Information					Cell-Group-Information	OPTIONAL,
	iE-Extensions							ProtocolExtensionContainer { { DRB-Confirm-Modified-Item-NG-RAN-ExtIEs } }	OPTIONAL,
	...
}

DRB-Confirm-Modified-Item-NG-RAN-ExtIEs		E1AP-PROTOCOL-EXTENSION ::= {
	...
}

DRB-Failed-List-EUTRAN	::= SEQUENCE (SIZE(1.. maxnoofDRBs)) OF DRB-Failed-Item-EUTRAN

DRB-Failed-Item-EUTRAN	::=	SEQUENCE {
	dRB-ID									DRB-ID,
	cause									Cause,
	iE-Extensions							ProtocolExtensionContainer { { DRB-Failed-Item-EUTRAN-ExtIEs } }	OPTIONAL,
	...
}

DRB-Failed-Item-EUTRAN-ExtIEs		E1AP-PROTOCOL-EXTENSION ::= {
	...
}

DRB-Failed-Mod-List-EUTRAN	::= SEQUENCE (SIZE(1.. maxnoofDRBs)) OF DRB-Failed-Mod-Item-EUTRAN

DRB-Failed-Mod-Item-EUTRAN	::=	SEQUENCE {
	dRB-ID									DRB-ID,
	cause									Cause,
	iE-Extensions							ProtocolExtensionContainer { { DRB-Failed-Mod-Item-EUTRAN-ExtIEs } }	OPTIONAL,
	...
}

DRB-Failed-Mod-Item-EUTRAN-ExtIEs		E1AP-PROTOCOL-EXTENSION ::= {
	...
}

DRB-Failed-List-NG-RAN	::= SEQUENCE (SIZE(1.. maxnoofDRBs)) OF DRB-Failed-Item-NG-RAN

DRB-Failed-Item-NG-RAN	::=	SEQUENCE {
	dRB-ID									DRB-ID,
	cause									Cause,
	iE-Extensions							ProtocolExtensionContainer { { DRB-Failed-Item-NG-RAN-ExtIEs } }	OPTIONAL,
	...
}

DRB-Failed-Item-NG-RAN-ExtIEs		E1AP-PROTOCOL-EXTENSION ::= {
	...
}

DRB-Failed-Mod-List-NG-RAN	::= SEQUENCE (SIZE(1.. maxnoofDRBs)) OF DRB-Failed-Mod-Item-NG-RAN

DRB-Failed-Mod-Item-NG-RAN	::=	SEQUENCE {
	dRB-ID									DRB-ID,
	cause									Cause,
	iE-Extensions							ProtocolExtensionContainer { { DRB-Failed-Mod-Item-NG-RAN-ExtIEs } }	OPTIONAL,
	...
}

DRB-Failed-Mod-Item-NG-RAN-ExtIEs		E1AP-PROTOCOL-EXTENSION ::= {
	...
}

DRB-Failed-To-Modify-List-EUTRAN	::= SEQUENCE (SIZE(1.. maxnoofDRBs)) OF DRB-Failed-To-Modify-Item-EUTRAN

DRB-Failed-To-Modify-Item-EUTRAN	::=	SEQUENCE {
	dRB-ID									DRB-ID,
	cause									Cause,
	iE-Extensions							ProtocolExtensionContainer { { DRB-Failed-To-Modify-Item-EUTRAN-ExtIEs } }	OPTIONAL,
	...
}

DRB-Failed-To-Modify-Item-EUTRAN-ExtIEs		E1AP-PROTOCOL-EXTENSION ::= {
	...
}

DRB-Failed-To-Modify-List-NG-RAN	::= SEQUENCE (SIZE(1.. maxnoofDRBs)) OF DRB-Failed-To-Modify-Item-NG-RAN

DRB-Failed-To-Modify-Item-NG-RAN	::=	SEQUENCE {
	dRB-ID									DRB-ID,
	cause									Cause,
	iE-Extensions							ProtocolExtensionContainer { { DRB-Failed-To-Modify-Item-NG-RAN-ExtIEs } }	OPTIONAL,
	...
}

DRB-Failed-To-Modify-Item-NG-RAN-ExtIEs		E1AP-PROTOCOL-EXTENSION ::= {
	...
}

DRB-ID	::=	INTEGER (1..32, ...)

DRB-Modified-List-EUTRAN	::= SEQUENCE (SIZE(1.. maxnoofDRBs)) OF DRB-Modified-Item-EUTRAN

DRB-Modified-Item-EUTRAN	::=	SEQUENCE {
	dRB-ID									DRB-ID, 
	s1-DL-UP-TNL-Information				UP-TNL-Information						OPTIONAL,
	pDCP-SN-Status-Information				PDCP-SN-Status-Information				OPTIONAL,
	uL-UP-Transport-Parameters				UP-Parameters							OPTIONAL,
	iE-Extensions							ProtocolExtensionContainer { { DRB-Modified-Item-EUTRAN-ExtIEs } }	OPTIONAL,
	...
}

DRB-Modified-Item-EUTRAN-ExtIEs		E1AP-PROTOCOL-EXTENSION ::= {
	...
}

DRB-Modified-List-NG-RAN	::= SEQUENCE (SIZE(1.. maxnoofDRBs)) OF DRB-Modified-Item-NG-RAN

DRB-Modified-Item-NG-RAN	::=	SEQUENCE {
	dRB-ID										DRB-ID,
	uL-UP-Transport-Parameters					UP-Parameters							OPTIONAL,
	pDCP-SN-Status-Information					PDCP-SN-Status-Information				OPTIONAL,	
	flow-Setup-List								QoS-Flow-List							OPTIONAL,
	flow-Failed-List							QoS-Flow-Failed-List					OPTIONAL,
	iE-Extensions							ProtocolExtensionContainer { { DRB-Modified-Item-NG-RAN-ExtIEs } }	OPTIONAL,
	...
}

DRB-Modified-Item-NG-RAN-ExtIEs		E1AP-PROTOCOL-EXTENSION ::= {
	...
}

DRB-Required-To-Modify-List-EUTRAN ::= SEQUENCE (SIZE(1.. maxnoofDRBs)) OF DRB-Required-To-Modify-Item-EUTRAN

DRB-Required-To-Modify-Item-EUTRAN	::=	SEQUENCE {
	dRB-ID									DRB-ID,
	s1-DL-UP-TNL-Information				UP-TNL-Information							OPTIONAL,
	gNB-CU-UP-CellGroupRelatedConfiguration	GNB-CU-UP-CellGroupRelatedConfiguration		OPTIONAL,
	cause									Cause		OPTIONAL,
	iE-Extensions							ProtocolExtensionContainer { { DRB-Required-To-Modify-Item-EUTRAN-ExtIEs } }	OPTIONAL,
	...
}

DRB-Required-To-Modify-Item-EUTRAN-ExtIEs		E1AP-PROTOCOL-EXTENSION ::= {
	...
}

DRB-Required-To-Modify-List-NG-RAN ::= SEQUENCE (SIZE(1.. maxnoofDRBs)) OF DRB-Required-To-Modify-Item-NG-RAN

DRB-Required-To-Modify-Item-NG-RAN	::=	SEQUENCE {
	dRB-ID									DRB-ID,
	gNB-CU-UP-CellGroupRelatedConfiguration	GNB-CU-UP-CellGroupRelatedConfiguration		OPTIONAL,
	flow-To-Remove							QoS-Flow-List								OPTIONAL,
	cause									Cause		OPTIONAL,
	iE-Extensions							ProtocolExtensionContainer { { DRB-Required-To-Modify-Item-NG-RAN-ExtIEs } }	OPTIONAL,
	...
}

DRB-Required-To-Modify-Item-NG-RAN-ExtIEs		E1AP-PROTOCOL-EXTENSION ::= {
	...
}


DRB-Setup-List-EUTRAN	::= SEQUENCE (SIZE(1.. maxnoofDRBs)) OF DRB-Setup-Item-EUTRAN

DRB-Setup-Item-EUTRAN	::=	SEQUENCE {
	dRB-ID									DRB-ID,
	s1-DL-UP-TNL-Information				UP-TNL-Information,
	data-Forwarding-Information-Response	Data-Forwarding-Information		OPTIONAL,
	uL-UP-Transport-Parameters				UP-Parameters,
	s1-DL-UP-Unchanged						ENUMERATED {true, ...}		OPTIONAL,
	iE-Extensions							ProtocolExtensionContainer { { DRB-Setup-Item-EUTRAN-ExtIEs } }	OPTIONAL,
	...
}

DRB-Setup-Item-EUTRAN-ExtIEs		E1AP-PROTOCOL-EXTENSION ::= {
	...
}

DRB-Setup-Mod-List-EUTRAN	::= SEQUENCE (SIZE(1.. maxnoofDRBs)) OF DRB-Setup-Mod-Item-EUTRAN

DRB-Setup-Mod-Item-EUTRAN	::=	SEQUENCE {
	dRB-ID									DRB-ID,
	s1-DL-UP-TNL-Information				UP-TNL-Information,
	data-Forwarding-Information-Response	Data-Forwarding-Information		OPTIONAL,
	uL-UP-Transport-Parameters				UP-Parameters,
	iE-Extensions							ProtocolExtensionContainer { { DRB-Setup-Mod-Item-EUTRAN-ExtIEs } }	OPTIONAL,
	...
}

DRB-Setup-Mod-Item-EUTRAN-ExtIEs		E1AP-PROTOCOL-EXTENSION ::= {
	...
}

DRB-Setup-List-NG-RAN	::= SEQUENCE (SIZE(1.. maxnoofDRBs)) OF DRB-Setup-Item-NG-RAN

DRB-Setup-Item-NG-RAN	::=	SEQUENCE {
	dRB-ID										DRB-ID,
	dRB-data-Forwarding-Information-Response	Data-Forwarding-Information		OPTIONAL,
	uL-UP-Transport-Parameters					UP-Parameters,
	flow-Setup-List								QoS-Flow-List,
	flow-Failed-List							QoS-Flow-Failed-List	OPTIONAL,
	iE-Extensions								ProtocolExtensionContainer { { DRB-Setup-Item-NG-RAN-ExtIEs } }	OPTIONAL,
	...
}

DRB-Setup-Item-NG-RAN-ExtIEs		E1AP-PROTOCOL-EXTENSION ::= {
	...
}

DRB-Setup-Mod-List-NG-RAN	::= SEQUENCE (SIZE(1.. maxnoofDRBs)) OF DRB-Setup-Mod-Item-NG-RAN

DRB-Setup-Mod-Item-NG-RAN	::=	SEQUENCE {
	dRB-ID										DRB-ID,
	dRB-data-Forwarding-Information-Response	Data-Forwarding-Information		OPTIONAL,
	uL-UP-Transport-Parameters					UP-Parameters,
	flow-Setup-List								QoS-Flow-List,
	flow-Failed-List							QoS-Flow-Failed-List	OPTIONAL,
	iE-Extensions								ProtocolExtensionContainer { { DRB-Setup-Mod-Item-NG-RAN-ExtIEs } }	OPTIONAL,
	...
}

DRB-Setup-Mod-Item-NG-RAN-ExtIEs		E1AP-PROTOCOL-EXTENSION ::= {
	...
}

DRB-Status-Item	::= SEQUENCE {
	dRB-ID						DRB-ID,
	pDCP-DL-Count				PDCP-Count		OPTIONAL,
	pDCP-UL-Count				PDCP-Count		OPTIONAL,
	iE-Extensions	ProtocolExtensionContainer { { DRB-Status-ItemExtIEs } }	OPTIONAL,
	...
}

DRB-Status-ItemExtIEs 	E1AP-PROTOCOL-EXTENSION ::= {
	...
}

DRBs-Subject-To-Counter-Check-List-EUTRAN	::= SEQUENCE (SIZE(1.. maxnoofDRBs)) OF DRBs-Subject-To-Counter-Check-Item-EUTRAN

DRBs-Subject-To-Counter-Check-Item-EUTRAN	::=	SEQUENCE {
	dRB-ID						DRB-ID,
	pDCP-UL-Count				PDCP-Count,
	pDCP-DL-Count				PDCP-Count,
	iE-Extensions		ProtocolExtensionContainer { { DRBs-Subject-To-Counter-Check-Item-EUTRAN-ExtIEs } }	OPTIONAL,
	...
}

DRBs-Subject-To-Counter-Check-Item-EUTRAN-ExtIEs		E1AP-PROTOCOL-EXTENSION ::= {
	...
}

DRBs-Subject-To-Counter-Check-List-NG-RAN	::= SEQUENCE (SIZE(1.. maxnoofDRBs)) OF DRBs-Subject-To-Counter-Check-Item-NG-RAN

DRBs-Subject-To-Counter-Check-Item-NG-RAN	::=	SEQUENCE {
	pDU-Session-ID				PDU-Session-ID,
	dRB-ID						DRB-ID,
	pDCP-UL-Count				PDCP-Count,
	pDCP-DL-Count				PDCP-Count,
	iE-Extensions			ProtocolExtensionContainer { { DRBs-Subject-To-Counter-Check-Item-NG-RAN-ExtIEs } }	OPTIONAL,
	...
}

DRBs-Subject-To-Counter-Check-Item-NG-RAN-ExtIEs		E1AP-PROTOCOL-EXTENSION ::= {
	...
}


DRB-To-Modify-List-EUTRAN	::= SEQUENCE (SIZE(1.. maxnoofDRBs)) OF DRB-To-Modify-Item-EUTRAN

DRB-To-Modify-Item-EUTRAN	::=	SEQUENCE {
	dRB-ID									DRB-ID,
	pDCP-Configuration						PDCP-Configuration						OPTIONAL,	
	eUTRAN-QoS								EUTRAN-QoS								OPTIONAL,
	s1-UL-UP-TNL-Information				UP-TNL-Information						OPTIONAL,	
	data-Forwarding-Information		Data-Forwarding-Information		OPTIONAL,
	pDCP-SN-Status-Request					PDCP-SN-Status-Request						OPTIONAL,
	pDCP-SN-Status-Information				PDCP-SN-Status-Information				OPTIONAL,
	dL-UP-Parameters						UP-Parameters							OPTIONAL,
	cell-Group-To-Add						Cell-Group-Information					OPTIONAL,
	cell-Group-To-Modify					Cell-Group-Information					OPTIONAL,
	cell-Group-To-Remove					Cell-Group-Information					OPTIONAL,
	dRB-Inactivity-Timer					Inactivity-Timer						OPTIONAL,
	iE-Extensions							ProtocolExtensionContainer { { DRB-To-Modify-Item-EUTRAN-ExtIEs } }	OPTIONAL,
	...
}

DRB-To-Modify-Item-EUTRAN-ExtIEs		E1AP-PROTOCOL-EXTENSION ::= {
	...
}

DRB-To-Modify-List-NG-RAN	::= SEQUENCE (SIZE(1.. maxnoofDRBs)) OF DRB-To-Modify-Item-NG-RAN

DRB-To-Modify-Item-NG-RAN	::=	SEQUENCE {
	dRB-ID										DRB-ID,
	sDAP-Configuration							SDAP-Configuration						OPTIONAL,	
	pDCP-Configuration							PDCP-Configuration						OPTIONAL,
	dRB-Data-Forwarding-Information		Data-Forwarding-Information		OPTIONAL,
	pDCP-SN-Status-Request							PDCP-SN-Status-Request						OPTIONAL,
	pdcp-SN-Status-Information					PDCP-SN-Status-Information				OPTIONAL,
	dL-UP-Parameters							UP-Parameters							OPTIONAL,
	cell-Group-To-Add							Cell-Group-Information					OPTIONAL,
	cell-Group-To-Modify						Cell-Group-Information					OPTIONAL,
	cell-Group-To-Remove						Cell-Group-Information					OPTIONAL,
	flow-Mapping-Information					QoS-Flow-QoS-Parameter-List				OPTIONAL,
	dRB-Inactivity-Timer						Inactivity-Timer						OPTIONAL,
	iE-Extensions								ProtocolExtensionContainer { { DRB-To-Modify-Item-NG-RAN-ExtIEs } }	OPTIONAL,
	...
}

DRB-To-Modify-Item-NG-RAN-ExtIEs		E1AP-PROTOCOL-EXTENSION ::= {
	{ID id-OldQoSFlowMap-ULendmarkerexpected	CRITICALITY reject	EXTENSION QoS-Flow-List	PRESENCE optional}|
	{ID id-DRB-QoS	CRITICALITY ignore	EXTENSION QoSFlowLevelQoSParameters	PRESENCE optional},
	...
}

DRB-To-Remove-List-EUTRAN	::= SEQUENCE (SIZE(1.. maxnoofDRBs)) OF DRB-To-Remove-Item-EUTRAN

DRB-To-Remove-Item-EUTRAN	::=	SEQUENCE {
	dRB-ID									DRB-ID,
	iE-Extensions							ProtocolExtensionContainer { { DRB-To-Remove-Item-EUTRAN-ExtIEs } }	OPTIONAL,
	...
}

DRB-To-Remove-Item-EUTRAN-ExtIEs		E1AP-PROTOCOL-EXTENSION ::= {
	...
}

DRB-Required-To-Remove-List-EUTRAN	::= SEQUENCE (SIZE(1.. maxnoofDRBs)) OF DRB-Required-To-Remove-Item-EUTRAN

DRB-Required-To-Remove-Item-EUTRAN	::=	SEQUENCE {
	dRB-ID									DRB-ID,
	cause									Cause,
	iE-Extensions							ProtocolExtensionContainer { { DRB-Required-To-Remove-Item-EUTRAN-ExtIEs } }	OPTIONAL,
	...
}

DRB-Required-To-Remove-Item-EUTRAN-ExtIEs		E1AP-PROTOCOL-EXTENSION ::= {
	...
}

DRB-To-Remove-List-NG-RAN	::= SEQUENCE (SIZE(1.. maxnoofDRBs)) OF DRB-To-Remove-Item-NG-RAN

DRB-To-Remove-Item-NG-RAN	::=	SEQUENCE {
	dRB-ID									DRB-ID,
	iE-Extensions							ProtocolExtensionContainer { { DRB-To-Remove-Item-NG-RAN-ExtIEs } }	OPTIONAL,
	...
}

DRB-To-Remove-Item-NG-RAN-ExtIEs		E1AP-PROTOCOL-EXTENSION ::= {
	...
}

DRB-Required-To-Remove-List-NG-RAN	::= SEQUENCE (SIZE(1.. maxnoofDRBs)) OF DRB-Required-To-Remove-Item-NG-RAN

DRB-Required-To-Remove-Item-NG-RAN	::=	SEQUENCE {
	dRB-ID									DRB-ID,
	cause									Cause,
	iE-Extensions							ProtocolExtensionContainer { { DRB-Required-To-Remove-Item-NG-RAN-ExtIEs } }	OPTIONAL,
	...
}

DRB-Required-To-Remove-Item-NG-RAN-ExtIEs		E1AP-PROTOCOL-EXTENSION ::= {
	...
}

DRB-To-Setup-List-EUTRAN	::= SEQUENCE (SIZE(1.. maxnoofDRBs)) OF DRB-To-Setup-Item-EUTRAN

DRB-To-Setup-Item-EUTRAN	::=	SEQUENCE {
	dRB-ID									DRB-ID,
	pDCP-Configuration						PDCP-Configuration,
	eUTRAN-QoS								EUTRAN-QoS,
	s1-UL-UP-TNL-Information				UP-TNL-Information,
	data-Forwarding-Information-Request		Data-Forwarding-Information-Request		OPTIONAL,
	cell-Group-Information					Cell-Group-Information,
	dL-UP-Parameters						UP-Parameters							OPTIONAL,
	dRB-Inactivity-Timer					Inactivity-Timer						OPTIONAL,
	existing-Allocated-S1-DL-UP-TNL-Info	UP-TNL-Information						OPTIONAL,
	iE-Extensions							ProtocolExtensionContainer { { DRB-To-Setup-Item-EUTRAN-ExtIEs } }	OPTIONAL,
	...
}

DRB-To-Setup-Item-EUTRAN-ExtIEs		E1AP-PROTOCOL-EXTENSION ::= {
	...
}

DRB-To-Setup-Mod-List-EUTRAN	::= SEQUENCE (SIZE(1.. maxnoofDRBs)) OF DRB-To-Setup-Mod-Item-EUTRAN

DRB-To-Setup-Mod-Item-EUTRAN	::=	SEQUENCE {
	dRB-ID										DRB-ID,
	pDCP-Configuration							PDCP-Configuration,
	eUTRAN-QoS									EUTRAN-QoS,
	s1-UL-UP-TNL-Information					UP-TNL-Information,
	data-Forwarding-Information-Request			Data-Forwarding-Information-Request		OPTIONAL,
	cell-Group-Information						Cell-Group-Information,
	dL-UP-Parameters							UP-Parameters							OPTIONAL,
	dRB-Inactivity-Timer						Inactivity-Timer						OPTIONAL,
	iE-Extensions								ProtocolExtensionContainer { { DRB-To-Setup-Mod-Item-EUTRAN-ExtIEs } }	OPTIONAL,
	...
}

DRB-To-Setup-Mod-Item-EUTRAN-ExtIEs		E1AP-PROTOCOL-EXTENSION ::= {
	...
}

DRB-To-Setup-List-NG-RAN	::= SEQUENCE (SIZE(1.. maxnoofDRBs)) OF DRB-To-Setup-Item-NG-RAN

DRB-To-Setup-Item-NG-RAN	::=	SEQUENCE {
	dRB-ID										DRB-ID,
	sDAP-Configuration							SDAP-Configuration,
	pDCP-Configuration							PDCP-Configuration,
	cell-Group-Information						Cell-Group-Information,
	qos-flow-Information-To-Be-Setup					QoS-Flow-QoS-Parameter-List,
	dRB-Data-Forwarding-Information-Request		Data-Forwarding-Information-Request		OPTIONAL,
	dRB-Inactivity-Timer						Inactivity-Timer	OPTIONAL,
	pDCP-SN-Status-Information								PDCP-SN-Status-Information								OPTIONAL,
	iE-Extensions							ProtocolExtensionContainer { { DRB-To-Setup-Item-NG-RAN-ExtIEs } }	OPTIONAL,
	...
}

DRB-To-Setup-Item-NG-RAN-ExtIEs		E1AP-PROTOCOL-EXTENSION ::= {
		{ID id-DRB-QoS	CRITICALITY ignore	EXTENSION QoSFlowLevelQoSParameters	PRESENCE optional},
	...
}

DRB-To-Setup-Mod-List-NG-RAN	::= SEQUENCE (SIZE(1.. maxnoofDRBs)) OF DRB-To-Setup-Mod-Item-NG-RAN

DRB-To-Setup-Mod-Item-NG-RAN	::=	SEQUENCE {
	dRB-ID										DRB-ID,
	sDAP-Configuration							SDAP-Configuration,
	pDCP-Configuration							PDCP-Configuration,
	cell-Group-Information						Cell-Group-Information,
	flow-Mapping-Information					QoS-Flow-QoS-Parameter-List,
	dRB-Data-Forwarding-Information-Request		Data-Forwarding-Information-Request		OPTIONAL,
	dRB-Inactivity-Timer						Inactivity-Timer					OPTIONAL,
	pDCP-SN-Status-Information				PDCP-SN-Status-Information					OPTIONAL,
	iE-Extensions								ProtocolExtensionContainer { { DRB-To-Setup-Mod-Item-NG-RAN-ExtIEs } }	OPTIONAL,
	...
}

DRB-To-Setup-Mod-Item-NG-RAN-ExtIEs		E1AP-PROTOCOL-EXTENSION ::= {
	{ID id-DRB-QoS	CRITICALITY ignore	EXTENSION QoSFlowLevelQoSParameters	PRESENCE optional},
	...
}

DRB-Usage-Report-List ::= SEQUENCE (SIZE(1..maxnooftimeperiods)) OF DRB-Usage-Report-Item

DRB-Usage-Report-Item	::= SEQUENCE {
	startTimeStamp					OCTET STRING (SIZE(4)),
	endTimeStamp					OCTET STRING (SIZE(4)),
	usageCountUL					INTEGER (0..18446744073709551615),
	usageCountDL					INTEGER (0..18446744073709551615),
	iE-Extensions					ProtocolExtensionContainer { { DRB-Usage-Report-Item-ExtIEs} } OPTIONAL,
	...
}

DRB-Usage-Report-Item-ExtIEs E1AP-PROTOCOL-EXTENSION ::= {
	...
}

Duplication-Activation	::=		ENUMERATED {
	active, 
	inactive,
	...
}


Dynamic5QIDescriptor	::= SEQUENCE {
	qoSPriorityLevel					QoSPriorityLevel,
	packetDelayBudget					PacketDelayBudget,
	packetErrorRate						PacketErrorRate,
	fiveQI								INTEGER (0..255, ...)								OPTIONAL,
	delayCritical						ENUMERATED {delay-critical, non-delay-critical}		OPTIONAL,
	averagingWindow 					AveragingWindow										OPTIONAL,
	maxDataBurstVolume					MaxDataBurstVolume									OPTIONAL,
	iE-Extensions					ProtocolExtensionContainer { { Dynamic5QIDescriptor-ExtIEs } } OPTIONAL
}

Dynamic5QIDescriptor-ExtIEs E1AP-PROTOCOL-EXTENSION ::= {
	...
}

DataDiscardRequired	::= 	ENUMERATED {
	required,
	...
}



EncryptionKey	::=	OCTET STRING

Endpoint-IP-address-and-port::= SEQUENCE {
	endpoint-IP-Address			TransportLayerAddress,
	portNumber					PortNumber,
	iE-Extensions							ProtocolExtensionContainer { { Endpoint-IP-address-and-port-ExtIEs} } OPTIONAL
}

Endpoint-IP-address-and-port-ExtIEs E1AP-PROTOCOL-EXTENSION ::= {
	...
}

EUTRANAllocationAndRetentionPriority ::= SEQUENCE {
	priorityLevel				PriorityLevel,
	pre-emptionCapability		Pre-emptionCapability,
	pre-emptionVulnerability	Pre-emptionVulnerability,
	iE-Extensions				ProtocolExtensionContainer { {EUTRANAllocationAndRetentionPriority-ExtIEs} } OPTIONAL,
	...
}

EUTRANAllocationAndRetentionPriority-ExtIEs E1AP-PROTOCOL-EXTENSION ::= {
	...
}


EUTRAN-QoS-Support-List ::= SEQUENCE (SIZE(1.. maxnoofEUTRANQOSParameters)) OF EUTRAN-QoS-Support-Item

EUTRAN-QoS-Support-Item ::= SEQUENCE {
	eUTRAN-QoS	EUTRAN-QoS,
	iE-Extensions			ProtocolExtensionContainer { { EUTRAN-QoS-Support-Item-ExtIEs } }	OPTIONAL
}

EUTRAN-QoS-Support-Item-ExtIEs	E1AP-PROTOCOL-EXTENSION ::= {
	...
}

EUTRAN-QoS	::= SEQUENCE {
	qCI										QCI,
	eUTRANallocationAndRetentionPriority	EUTRANAllocationAndRetentionPriority,
	gbrQosInformation						GBR-QosInformation										OPTIONAL,
	iE-Extensions							ProtocolExtensionContainer { { EUTRAN-QoS-ExtIEs } }	OPTIONAL,
	...
}

EUTRAN-QoS-ExtIEs E1AP-PROTOCOL-EXTENSION ::= {
	...
}





GNB-CU-CP-Name 				::= PrintableString(SIZE(1..150, ...))

GNB-CU-CP-UE-E1AP-ID		::= INTEGER (0..4294967295)

GNB-CU-UP-Capacity				::= INTEGER (0..255)

GNB-CU-UP-CellGroupRelatedConfiguration	 ::= SEQUENCE (SIZE(1.. maxnoofUPParameters)) OF GNB-CU-UP-CellGroupRelatedConfiguration-Item	

GNB-CU-UP-CellGroupRelatedConfiguration-Item ::= SEQUENCE {
	cell-Group-ID				Cell-Group-ID,
	uP-TNL-Information			UP-TNL-Information,
	uL-Configuration			UL-Configuration		OPTIONAL,
	iE-Extensions				ProtocolExtensionContainer { {GNB-CU-UP-CellGroupRelatedConfiguration-Item-ExtIEs } }	OPTIONAL
}

GNB-CU-UP-CellGroupRelatedConfiguration-Item-ExtIEs	E1AP-PROTOCOL-EXTENSION ::= {
	...
}

GNB-CU-UP-ID				::= INTEGER (0..68719476735)

GNB-CU-UP-Name 				::= PrintableString(SIZE(1..150, ...))

GNB-CU-UP-UE-E1AP-ID		::= INTEGER (0..4294967295) 

GNB-CU-CP-TNLA-Setup-Item::= SEQUENCE {
	tNLAssociationTransportLayerAddress		CP-TNL-Information,
	iE-Extensions							ProtocolExtensionContainer { { GNB-CU-CP-TNLA-Setup-Item-ExtIEs} } OPTIONAL,
	...
}

GNB-CU-CP-TNLA-Setup-Item-ExtIEs E1AP-PROTOCOL-EXTENSION ::= {
	...
}

GNB-CU-CP-TNLA-Failed-To-Setup-Item ::= SEQUENCE {
	tNLAssociationTransportLayerAddress		CP-TNL-Information,
	cause									Cause,
	iE-Extensions							ProtocolExtensionContainer { { GNB-CU-CP-TNLA-Failed-To-Setup-Item-ExtIEs} } OPTIONAL
}

GNB-CU-CP-TNLA-Failed-To-Setup-Item-ExtIEs E1AP-PROTOCOL-EXTENSION ::= {
	...
}

GNB-CU-CP-TNLA-To-Add-Item ::= SEQUENCE {
	tNLAssociationTransportLayerAddress		CP-TNL-Information,
	tNLAssociationUsage						TNLAssociationUsage,
	iE-Extensions							ProtocolExtensionContainer { { GNB-CU-CP-TNLA-To-Add-Item-ExtIEs} } OPTIONAL
}

GNB-CU-CP-TNLA-To-Add-Item-ExtIEs E1AP-PROTOCOL-EXTENSION ::= {
	...
}

GNB-CU-CP-TNLA-To-Remove-Item::= SEQUENCE {
	tNLAssociationTransportLayerAddress		CP-TNL-Information,
	iE-Extensions							ProtocolExtensionContainer { { GNB-CU-CP-TNLA-To-Remove-Item-ExtIEs} } OPTIONAL
}

GNB-CU-CP-TNLA-To-Remove-Item-ExtIEs E1AP-PROTOCOL-EXTENSION ::= {
	{ID id-TNLAssociationTransportLayerAddressgNBCUUP	CRITICALITY reject	EXTENSION CP-TNL-Information	PRESENCE optional},
	...
}

GNB-CU-CP-TNLA-To-Update-Item::= SEQUENCE {
	tNLAssociationTransportLayerAddress		CP-TNL-Information,
	tNLAssociationUsage						TNLAssociationUsage 	OPTIONAL,
	iE-Extensions							ProtocolExtensionContainer { { GNB-CU-CP-TNLA-To-Update-Item-ExtIEs} } OPTIONAL
}

GNB-CU-CP-TNLA-To-Update-Item-ExtIEs E1AP-PROTOCOL-EXTENSION ::= {
	...
}

GNB-CU-UP-TNLA-To-Remove-Item::= SEQUENCE {
	tNLAssociationTransportLayerAddress			CP-TNL-Information,
	tNLAssociationTransportLayerAddressgNBCUCP	CP-TNL-Information		OPTIONAL,
	iE-Extensions							ProtocolExtensionContainer { { GNB-CU-UP-TNLA-To-Remove-Item-ExtIEs} } OPTIONAL
}

GNB-CU-UP-TNLA-To-Remove-Item-ExtIEs E1AP-PROTOCOL-EXTENSION ::= {
	...
}

GBR-QosInformation ::= SEQUENCE {
	e-RAB-MaximumBitrateDL			BitRate,
	e-RAB-MaximumBitrateUL			BitRate,
	e-RAB-GuaranteedBitrateDL		BitRate,
	e-RAB-GuaranteedBitrateUL		BitRate,
	iE-Extensions					ProtocolExtensionContainer { { GBR-QosInformation-ExtIEs} } OPTIONAL,
	...
}

GBR-QosInformation-ExtIEs E1AP-PROTOCOL-EXTENSION ::= {
	...
}

GBR-QoSFlowInformation::= SEQUENCE {
	maxFlowBitRateDownlink			BitRate,
	maxFlowBitRateUplink			BitRate, 
	guaranteedFlowBitRateDownlink	BitRate,
	guaranteedFlowBitRateUplink		BitRate, 
	maxPacketLossRateDownlink		MaxPacketLossRate		OPTIONAL,
	maxPacketLossRateUplink			MaxPacketLossRate		OPTIONAL,
	iE-Extensions					ProtocolExtensionContainer { { GBR-QosFlowInformation-ExtIEs} } OPTIONAL,
	...
}

GBR-QosFlowInformation-ExtIEs E1AP-PROTOCOL-EXTENSION ::= {
	...
}

GTP-TEID				::= OCTET STRING (SIZE (4))

GTPTunnel				::= SEQUENCE {
	transportLayerAddress				TransportLayerAddress,
	gTP-TEID							GTP-TEID,
	iE-Extensions						ProtocolExtensionContainer { { GTPTunnel-ExtIEs} } OPTIONAL,
	...
}

GTPTunnel-ExtIEs E1AP-PROTOCOL-EXTENSION ::= {
	...
}

GNB-CU-UP-OverloadInformation ::= ENUMERATED {overloaded, not-overloaded}

GNB-DU-ID	::= INTEGER (0..68719476735)




HFN		::=		INTEGER	(0..4294967295)



IntegrityProtectionIndication ::= ENUMERATED {
	required,
	preferred,
	not-needed,
	...
}

IntegrityProtectionAlgorithm	::=	ENUMERATED {
	nIA0,
	i-128-NIA1,
	i-128-NIA2,
	i-128-NIA3,
	...
}

IntegrityProtectionKey	::= OCTET STRING

IntegrityProtectionResult ::= ENUMERATED {
	performed,
	not-performed,
	...
}

Inactivity-Timer	::=	INTEGER (1..7200, ...)









MaxDataBurstVolume  ::= INTEGER (0..4095, ...) 

MaximumIPdatarate ::= SEQUENCE {
	maxIPrate			MaxIPrate,
	iE-Extensions		ProtocolExtensionContainer { {MaximumIPdatarate-ExtIEs} }	OPTIONAL,
	...
}

MaximumIPdatarate-ExtIEs E1AP-PROTOCOL-EXTENSION ::= {
	...
}

MaxIPrate ::= ENUMERATED {
	bitrate64kbs,
	max-UErate,
	...
}

MaxPacketLossRate ::= INTEGER (0..1000, ...)

MRDC-Data-Usage-Report-Item ::= SEQUENCE {
	startTimeStamp				OCTET STRING (SIZE(4)),
	endTimeStamp				OCTET STRING (SIZE(4)),
	usageCountUL				INTEGER (0..18446744073709551615),
	usageCountDL				INTEGER (0..18446744073709551615),
	iE-Extensions				ProtocolExtensionContainer { { MRDC-Data-Usage-Report-Item-ExtIEs} } OPTIONAL,
...
}

MRDC-Data-Usage-Report-Item-ExtIEs E1AP-PROTOCOL-EXTENSION ::= {
	...
}

MRDC-Usage-Information ::= SEQUENCE {
	data-Usage-per-PDU-Session-Report		Data-Usage-per-PDU-Session-Report			OPTIONAL,
	data-Usage-per-QoS-Flow-List			Data-Usage-per-QoS-Flow-List				OPTIONAL,
	iE-Extensions				ProtocolExtensionContainer { { MRDC-Usage-Information-ExtIEs} } OPTIONAL,
...
}

MRDC-Usage-Information-ExtIEs E1AP-PROTOCOL-EXTENSION ::= {
	...
}



NetworkInstance ::= INTEGER (1..256, ...)

New-UL-TNL-Information-Required::= 	ENUMERATED {
	required,
	...
}
NGRANAllocationAndRetentionPriority ::= SEQUENCE {
	priorityLevel				PriorityLevel,
	pre-emptionCapability		Pre-emptionCapability,
	pre-emptionVulnerability	Pre-emptionVulnerability,
	iE-Extensions				ProtocolExtensionContainer { {NGRANAllocationAndRetentionPriority-ExtIEs} } OPTIONAL
}

NGRANAllocationAndRetentionPriority-ExtIEs E1AP-PROTOCOL-EXTENSION ::= {
	...
}

NG-RAN-QoS-Support-List ::= SEQUENCE (SIZE(1.. maxnoofNGRANQOSParameters)) OF NG-RAN-QoS-Support-Item

NG-RAN-QoS-Support-Item ::= SEQUENCE {
	non-Dynamic5QIDescriptor	Non-Dynamic5QIDescriptor,
	iE-Extensions				ProtocolExtensionContainer { { NG-RAN-QoS-Support-Item-ExtIEs } }	OPTIONAL
}

NG-RAN-QoS-Support-Item-ExtIEs	E1AP-PROTOCOL-EXTENSION ::= {
	...
}

Non-Dynamic5QIDescriptor	::= SEQUENCE {
	fiveQI						INTEGER (0..255, ...),
	qoSPriorityLevel			QoSPriorityLevel				OPTIONAL,
	averagingWindow 			AveragingWindow					OPTIONAL,
	maxDataBurstVolume			MaxDataBurstVolume				OPTIONAL,
	iE-Extensions	ProtocolExtensionContainer { { Non-Dynamic5QIDescriptor-ExtIEs } } OPTIONAL
}

Non-Dynamic5QIDescriptor-ExtIEs E1AP-PROTOCOL-EXTENSION ::= {
	...
}

NR-Cell-Identity	::=		BIT STRING (SIZE(36))

NR-CGI ::= SEQUENCE {
	pLMN-Identity			PLMN-Identity,
	nR-Cell-Identity		NR-Cell-Identity,
	iE-Extensions			ProtocolExtensionContainer { { NR-CGI-ExtIEs } }	OPTIONAL
}

NR-CGI-ExtIEs	E1AP-PROTOCOL-EXTENSION ::= {
	...
}

NR-CGI-Support-List ::= SEQUENCE (SIZE(1.. maxnoofNRCGI)) OF NR-CGI-Support-Item

NR-CGI-Support-Item ::= SEQUENCE {
	nR-CGI	NR-CGI,
	iE-Extensions				ProtocolExtensionContainer { { NR-CGI-Support-Item-ExtIEs } }	OPTIONAL
}

NR-CGI-Support-Item-ExtIEs	E1AP-PROTOCOL-EXTENSION ::= {
	...
}



OutOfOrderDelivery	::=	ENUMERATED	{
	true,
	...
}




PacketDelayBudget ::= INTEGER (0..1023, ...) 

PacketErrorRate ::= SEQUENCE {
	pER-Scalar			PER-Scalar,
	pER-Exponent		PER-Exponent,
	iE-Extensions		ProtocolExtensionContainer { {PacketErrorRate-ExtIEs} }	OPTIONAL,
	...
}

PacketErrorRate-ExtIEs E1AP-PROTOCOL-EXTENSION ::= {
	...
}

PER-Scalar ::= INTEGER (0..9, ...)
PER-Exponent ::= INTEGER (0..9, ...)

PDCP-Configuration	::=	SEQUENCE {
	
	pDCP-SN-Size-UL							PDCP-SN-Size,
	pDCP-SN-Size-DL							PDCP-SN-Size,
	rLC-Mode								RLC-Mode,
	rOHC-Parameters							ROHC-Parameters			OPTIONAL,
	t-ReorderingTimer						T-ReorderingTimer		OPTIONAL,
	discardTimer							DiscardTimer			OPTIONAL,
	uLDataSplitThreshold					ULDataSplitThreshold	OPTIONAL,
	pDCP-Duplication						PDCP-Duplication		OPTIONAL,
	pDCP-Reestablishment					PDCP-Reestablishment	OPTIONAL,
	pDCP-DataRecovery						PDCP-DataRecovery		OPTIONAL,
	duplication-Activation				Duplication-Activation		OPTIONAL,
	outOfOrderDelivery						OutOfOrderDelivery		OPTIONAL,
	iE-Extensions							ProtocolExtensionContainer	{ { PDCP-Configuration-ExtIEs } }	OPTIONAL,
	...
}

PDCP-Configuration-ExtIEs		E1AP-PROTOCOL-EXTENSION ::= {
	...
}

PDCP-Count	::=	SEQUENCE {
	pDCP-SN				PDCP-SN,
	hFN					HFN,
	iE-Extensions							ProtocolExtensionContainer	{ { PDCP-Count-ExtIEs } }	OPTIONAL,
	...
}

PDCP-Count-ExtIEs		E1AP-PROTOCOL-EXTENSION ::= {
	...
}	
	
PDCP-SN-Status-Request	::=		ENUMERATED {
	requested,
	...
}

PDCP-DataRecovery	::=	ENUMERATED	{
	true,
	...
}

PDCP-Duplication	::=	ENUMERATED	{
	true,
	...
}

PDCP-Reestablishment	::=	ENUMERATED	{
	true,
	...
}

PDU-Session-Resource-Data-Usage-List	::= SEQUENCE (SIZE(1.. maxnoofPDUSessionResource)) OF PDU-Session-Resource-Data-Usage-Item

PDU-Session-Resource-Data-Usage-Item	::= SEQUENCE {
	pDU-Session-ID							PDU-Session-ID,
	mRDC-Usage-Information						MRDC-Usage-Information,
	iE-Extensions							ProtocolExtensionContainer	{ { PDU-Session-Resource-Data-Usage-Item-ExtIEs } }	OPTIONAL,
	...
}

PDU-Session-Resource-Data-Usage-Item-ExtIEs		E1AP-PROTOCOL-EXTENSION ::= {
	...
}

PDCP-SN		::=		INTEGER	(0..262143)

PDCP-SN-Size	::=	ENUMERATED	{
	s-12,
	s-18,
	...
}

PDCP-SN-Status-Information ::= SEQUENCE {
	pdcpStatusTransfer-UL	DRBBStatusTransfer,
	pdcpStatusTransfer-DL	PDCP-Count,
	iE-Extension		ProtocolExtensionContainer { {DRBsSubjectToStatusTransfer-Item-ExtIEs} }	OPTIONAL,
	...
}

DRBsSubjectToStatusTransfer-Item-ExtIEs E1AP-PROTOCOL-EXTENSION ::= {
	...
}

DRBBStatusTransfer ::= SEQUENCE {
	receiveStatusofPDCPSDU	BIT STRING (SIZE(1..131072))										OPTIONAL,
	countValue				PDCP-Count,
	iE-Extension			ProtocolExtensionContainer { {DRBBStatusTransfer-ExtIEs} }	OPTIONAL,
	...
}

DRBBStatusTransfer-ExtIEs E1AP-PROTOCOL-EXTENSION ::= {
	...
}

PDU-Session-ID	::=	INTEGER (0..255)

PDU-Session-Resource-Activity	::= ENUMERATED {
	active,
	not-active,
	...
}

PDU-Session-Resource-Activity-List ::= SEQUENCE (SIZE(1.. maxnoofPDUSessionResource)) OF PDU-Session-Resource-Activity-Item

PDU-Session-Resource-Activity-Item	::= SEQUENCE {
	pDU-Session-ID									PDU-Session-ID,
	pDU-Session-Resource-Activity					PDU-Session-Resource-Activity,
	iE-Extensions	ProtocolExtensionContainer 		{ { PDU-Session-Resource-Activity-ItemExtIEs } }	OPTIONAL,
	...
}

PDU-Session-Resource-Activity-ItemExtIEs 	E1AP-PROTOCOL-EXTENSION ::= {
	...
}


PDU-Session-Resource-Confirm-Modified-List	::= SEQUENCE (SIZE(1.. maxnoofPDUSessionResource)) OF PDU-Session-Resource-Confirm-Modified-Item

PDU-Session-Resource-Confirm-Modified-Item	::=	SEQUENCE {
	pDU-Session-ID							PDU-Session-ID,
	dRB-Confirm-Modified-List-NG-RAN		DRB-Confirm-Modified-List-NG-RAN	OPTIONAL,
	iE-Extensions							ProtocolExtensionContainer	{ { PDU-Session-Resource-Confirm-Modified-Item-ExtIEs } }	OPTIONAL,
	...
}

PDU-Session-Resource-Confirm-Modified-Item-ExtIEs		E1AP-PROTOCOL-EXTENSION ::= {
	...
}

PDU-Session-Resource-Failed-List	::= SEQUENCE (SIZE(1.. maxnoofPDUSessionResource)) OF PDU-Session-Resource-Failed-Item

PDU-Session-Resource-Failed-Item	::=	SEQUENCE {
	pDU-Session-ID							PDU-Session-ID,
	cause									Cause,
	iE-Extensions							ProtocolExtensionContainer	{ { PDU-Session-Resource-Failed-Item-ExtIEs } }	OPTIONAL,
	...
}

PDU-Session-Resource-Failed-Item-ExtIEs		E1AP-PROTOCOL-EXTENSION ::= {
	...
}

PDU-Session-Resource-Failed-Mod-List	::= SEQUENCE (SIZE(1.. maxnoofPDUSessionResource)) OF PDU-Session-Resource-Failed-Mod-Item

PDU-Session-Resource-Failed-Mod-Item	::=	SEQUENCE {
	pDU-Session-ID							PDU-Session-ID,
	cause									Cause,
	iE-Extensions							ProtocolExtensionContainer	{ { PDU-Session-Resource-Failed-Mod-Item-ExtIEs } }	OPTIONAL,
	...
}

PDU-Session-Resource-Failed-Mod-Item-ExtIEs		E1AP-PROTOCOL-EXTENSION ::= {
	...
}

PDU-Session-Resource-Failed-To-Modify-List	::= SEQUENCE (SIZE(1.. maxnoofPDUSessionResource)) OF PDU-Session-Resource-Failed-To-Modify-Item

PDU-Session-Resource-Failed-To-Modify-Item	::=	SEQUENCE {
	pDU-Session-ID							PDU-Session-ID,
	cause									Cause,
	iE-Extensions							ProtocolExtensionContainer	{ { PDU-Session-Resource-Failed-To-Modify-Item-ExtIEs } }	OPTIONAL,
	...
}

PDU-Session-Resource-Failed-To-Modify-Item-ExtIEs		E1AP-PROTOCOL-EXTENSION ::= {
	...
}

PDU-Session-Resource-Modified-List	::= SEQUENCE (SIZE(1.. maxnoofPDUSessionResource)) OF PDU-Session-Resource-Modified-Item

PDU-Session-Resource-Modified-Item	::=	SEQUENCE {
	pDU-Session-ID							PDU-Session-ID,
	nG-DL-UP-TNL-Information				UP-TNL-Information						OPTIONAL,
	securityResult							SecurityResult							OPTIONAL,
	pDU-Session-Data-Forwarding-Information-Response		Data-Forwarding-Information		OPTIONAL,
	dRB-Setup-List-NG-RAN					DRB-Setup-List-NG-RAN					OPTIONAL,
	dRB-Failed-List-NG-RAN				DRB-Failed-List-NG-RAN				OPTIONAL,
	dRB-Modified-List-NG-RAN				DRB-Modified-List-NG-RAN				OPTIONAL,
	dRB-Failed-To-Modify-List-NG-RAN		DRB-Failed-To-Modify-List-NG-RAN		OPTIONAL,
	iE-Extensions							ProtocolExtensionContainer	{ { PDU-Session-Resource-Modified-Item-ExtIEs } }	OPTIONAL,
	...
}

PDU-Session-Resource-Modified-Item-ExtIEs		E1AP-PROTOCOL-EXTENSION ::= {
	...
}

PDU-Session-Resource-Required-To-Modify-List	::= SEQUENCE (SIZE(1.. maxnoofPDUSessionResource)) OF PDU-Session-Resource-Required-To-Modify-Item

PDU-Session-Resource-Required-To-Modify-Item	::=	SEQUENCE {
	pDU-Session-ID							PDU-Session-ID,
	nG-DL-UP-TNL-Information				UP-TNL-Information						OPTIONAL,
	dRB-Required-To-Modify-List-NG-RAN		DRB-Required-To-Modify-List-NG-RAN		OPTIONAL,
	dRB-Required-To-Remove-List-NG-RAN				DRB-Required-To-Remove-List-NG-RAN				OPTIONAL,
	iE-Extensions							ProtocolExtensionContainer	{ { PDU-Session-Resource-Required-To-Modify-Item-ExtIEs } }	OPTIONAL,
	...
}

PDU-Session-Resource-Required-To-Modify-Item-ExtIEs		E1AP-PROTOCOL-EXTENSION ::= {
	...
}	

PDU-Session-Resource-Setup-List	::= SEQUENCE (SIZE(1.. maxnoofPDUSessionResource)) OF PDU-Session-Resource-Setup-Item

PDU-Session-Resource-Setup-Item	::=	SEQUENCE {
	pDU-Session-ID							PDU-Session-ID,
	securityResult							SecurityResult				OPTIONAL,
	nG-DL-UP-TNL-Information				UP-TNL-Information,
	pDU-Session-Data-Forwarding-Information-Response		Data-Forwarding-Information		OPTIONAL,
	nG-DL-UP-Unchanged						ENUMERATED {true, ...}		OPTIONAL,
	dRB-Setup-List-NG-RAN					DRB-Setup-List-NG-RAN,
	dRB-Failed-List-NG-RAN					DRB-Failed-List-NG-RAN		OPTIONAL,
	iE-Extensions							ProtocolExtensionContainer	{ { PDU-Session-Resource-Setup-Item-ExtIEs } }	OPTIONAL,
	...
}

PDU-Session-Resource-Setup-Item-ExtIEs		E1AP-PROTOCOL-EXTENSION ::= {
	...
}	

PDU-Session-Resource-Setup-Mod-List	::= SEQUENCE (SIZE(1.. maxnoofPDUSessionResource)) OF PDU-Session-Resource-Setup-Mod-Item

PDU-Session-Resource-Setup-Mod-Item	::=	SEQUENCE {
	pDU-Session-ID											PDU-Session-ID,
	securityResult											SecurityResult								OPTIONAL,
	nG-DL-UP-TNL-Information								UP-TNL-Information,
	pDU-Session-Data-Forwarding-Information-Response		Data-Forwarding-Information		OPTIONAL,
	dRB-Setup-Mod-List-NG-RAN								DRB-Setup-Mod-List-NG-RAN,
	dRB-Failed-Mod-List-NG-RAN								DRB-Failed-Mod-List-NG-RAN					OPTIONAL,
	iE-Extensions											ProtocolExtensionContainer	{ { PDU-Session-Resource-Setup-Mod-Item-ExtIEs } }	OPTIONAL,
	...
}

PDU-Session-Resource-Setup-Mod-Item-ExtIEs		E1AP-PROTOCOL-EXTENSION ::= {
	...
}

PDU-Session-Resource-To-Modify-List	::= SEQUENCE (SIZE(1.. maxnoofPDUSessionResource)) OF PDU-Session-Resource-To-Modify-Item

PDU-Session-Resource-To-Modify-Item	::=	SEQUENCE {
	pDU-Session-ID										PDU-Session-ID,
	securityIndication									SecurityIndication						OPTIONAL,
	pDU-Session-Resource-DL-AMBR						BitRate									OPTIONAL,
	nG-UL-UP-TNL-Information							UP-TNL-Information						OPTIONAL,
	pDU-Session-Data-Forwarding-Information-Request		Data-Forwarding-Information-Request		OPTIONAL,
	pDU-Session-Data-Forwarding-Information	Data-Forwarding-Information	OPTIONAL,
	pDU-Session-Inactivity-Timer						Inactivity-Timer						OPTIONAL,
	networkInstance										NetworkInstance							OPTIONAL,
	dRB-To-Setup-List-NG-RAN							DRB-To-Setup-List-NG-RAN				OPTIONAL,
	dRB-To-Modify-List-NG-RAN							DRB-To-Modify-List-NG-RAN				OPTIONAL,
	dRB-To-Remove-List-NG-RAN					DRB-To-Remove-List-NG-RAN		OPTIONAL,
	iE-Extensions										ProtocolExtensionContainer	{ { PDU-Session-Resource-To-Modify-Item-ExtIEs } }	OPTIONAL,
	...
}

PDU-Session-Resource-To-Modify-Item-ExtIEs		E1AP-PROTOCOL-EXTENSION ::= {
	{ID id-SNSSAI		CRITICALITY reject	EXTENSION SNSSAI		PRESENCE optional}|
	{ ID id-CommonNetworkInstance						CRITICALITY ignore	EXTENSION CommonNetworkInstance								PRESENCE optional	},
	...
}

PDU-Session-Resource-To-Remove-List	::= SEQUENCE (SIZE(1.. maxnoofPDUSessionResource)) OF PDU-Session-Resource-To-Remove-Item

PDU-Session-Resource-To-Remove-Item	::=	SEQUENCE {
	pDU-Session-ID							PDU-Session-ID,
	iE-Extensions							ProtocolExtensionContainer	{ { PDU-Session-Resource-To-Remove-Item-ExtIEs } }	OPTIONAL,
	...
}

PDU-Session-Resource-To-Remove-Item-ExtIEs		E1AP-PROTOCOL-EXTENSION ::= {
	{ID id-Cause		CRITICALITY ignore	EXTENSION Cause		PRESENCE optional},
	...
}

PDU-Session-Resource-To-Setup-List	::= SEQUENCE (SIZE(1.. maxnoofPDUSessionResource)) OF PDU-Session-Resource-To-Setup-Item

PDU-Session-Resource-To-Setup-Item	::=	SEQUENCE {
	pDU-Session-ID							PDU-Session-ID,
	pDU-Session-Type						PDU-Session-Type,
	sNSSAI									SNSSAI,
	securityIndication						SecurityIndication,
	pDU-Session-Resource-DL-AMBR			BitRate						OPTIONAL,
	nG-UL-UP-TNL-Information				UP-TNL-Information,
	pDU-Session-Data-Forwarding-Information-Request		Data-Forwarding-Information-Request		OPTIONAL,
	pDU-Session-Inactivity-Timer			Inactivity-Timer	OPTIONAL,
	existing-Allocated-NG-DL-UP-TNL-Info	UP-TNL-Information		OPTIONAL,
	networkInstance							NetworkInstance		OPTIONAL,
	dRB-To-Setup-List-NG-RAN				DRB-To-Setup-List-NG-RAN,
	iE-Extensions							ProtocolExtensionContainer	{ { PDU-Session-Resource-To-Setup-Item-ExtIEs } }	OPTIONAL,
	...
}

PDU-Session-Resource-To-Setup-Item-ExtIEs		E1AP-PROTOCOL-EXTENSION ::= {
	{ ID id-CommonNetworkInstance						CRITICALITY ignore	EXTENSION CommonNetworkInstance								PRESENCE optional	},
	...
}

PDU-Session-Resource-To-Setup-Mod-List	::= SEQUENCE (SIZE(1.. maxnoofPDUSessionResource)) OF PDU-Session-Resource-To-Setup-Mod-Item

PDU-Session-Resource-To-Setup-Mod-Item	::=	SEQUENCE {
	pDU-Session-ID										PDU-Session-ID,
	pDU-Session-Type									PDU-Session-Type,
	sNSSAI												SNSSAI,
	securityIndication									SecurityIndication,
	pDU-Session-Resource-AMBR							BitRate									OPTIONAL,
	nG-UL-UP-TNL-Information							UP-TNL-Information,
	pDU-Session-Data-Forwarding-Information-Request		Data-Forwarding-Information-Request		OPTIONAL,
	pDU-Session-Inactivity-Timer						Inactivity-Timer						OPTIONAL, 
	dRB-To-Setup-Mod-List-NG-RAN						DRB-To-Setup-Mod-List-NG-RAN,
	iE-Extensions										ProtocolExtensionContainer	{ { PDU-Session-Resource-To-Setup-Mod-Item-ExtIEs } }	OPTIONAL,
	...
}

PDU-Session-Resource-To-Setup-Mod-Item-ExtIEs		E1AP-PROTOCOL-EXTENSION ::= {
	{ID id-NetworkInstance		CRITICALITY ignore	EXTENSION NetworkInstance		PRESENCE optional}|
	{ID id-CommonNetworkInstance	CRITICALITY ignore	EXTENSION CommonNetworkInstance	PRESENCE optional},
	...
}

PDU-Session-To-Notify-List	::= SEQUENCE (SIZE(1.. maxnoofPDUSessionResource)) OF PDU-Session-To-Notify-Item

PDU-Session-To-Notify-Item	::=	SEQUENCE {
	pDU-Session-ID							PDU-Session-ID,
	qoS-Flow-List							QoS-Flow-List,
	iE-Extensions							ProtocolExtensionContainer	{ { PDU-Session-To-Notify-Item-ExtIEs } }	OPTIONAL,
	...
}

PDU-Session-To-Notify-Item-ExtIEs		E1AP-PROTOCOL-EXTENSION ::= {
	...
}

PDU-Session-Type ::= ENUMERATED {
	ipv4,
	ipv6,
	ipv4v6,
	ethernet,
	unstructured,
	...
}

PLMN-Identity ::= OCTET STRING (SIZE(3)) 

PortNumber ::= BIT STRING (SIZE(16))

PPI ::= INTEGER (0..7, ...)

PriorityLevel	::= INTEGER { spare (0), highest (1), lowest (14), no-priority (15) } (0..15)

Pre-emptionCapability ::= ENUMERATED {
	shall-not-trigger-pre-emption,
	may-trigger-pre-emption
}

Pre-emptionVulnerability ::= ENUMERATED {
	not-pre-emptable,
	pre-emptable
}



QCI ::= INTEGER (0..255)

QoS-Characteristics ::= CHOICE {
	non-Dynamic-5QI				Non-Dynamic5QIDescriptor,
	dynamic-5QI					Dynamic5QIDescriptor,
	choice-extension			ProtocolIE-SingleContainer	{{QoS-Characteristics-ExtIEs}}
}

QoS-Characteristics-ExtIEs E1AP-PROTOCOL-IES ::= {
	...
}

QoS-Flow-Identifier	::=	INTEGER (0..63)

QoS-Flow-List	::= SEQUENCE (SIZE(1.. maxnoofQoSFlows)) OF QoS-Flow-Item

QoS-Flow-Item	::=	SEQUENCE {
	qoS-Flow-Identifier						QoS-Flow-Identifier,
	iE-Extensions							ProtocolExtensionContainer	{ { QoS-Flow-Item-ExtIEs } }	OPTIONAL,
	...
}

QoS-Flow-Item-ExtIEs		E1AP-PROTOCOL-EXTENSION ::= {
	{ID id-QoSFlowMappingIndication		CRITICALITY ignore	EXTENSION QoS-Flow-Mapping-Indication		PRESENCE optional},
	...
}

QoS-Flow-Failed-List	::= SEQUENCE (SIZE(1.. maxnoofQoSFlows)) OF QoS-Flow-Failed-Item

QoS-Flow-Failed-Item	::=	SEQUENCE {
	qoS-Flow-Identifier						QoS-Flow-Identifier,
	cause									Cause,
	iE-Extensions							ProtocolExtensionContainer	{ { QoS-Flow-Failed-Item-ExtIEs } }	OPTIONAL,
	...
}

QoS-Flow-Failed-Item-ExtIEs		E1AP-PROTOCOL-EXTENSION ::= {
	...
}

QoS-Flow-Mapping-List	::= SEQUENCE (SIZE(1.. maxnoofQoSFlows)) OF QoS-Flow-Mapping-Item

QoS-Flow-Mapping-Item	::=	SEQUENCE {
	qoS-Flow-Identifier						QoS-Flow-Identifier,
	qoSFlowMappingIndication						QoS-Flow-Mapping-Indication		OPTIONAL,
	iE-Extensions							ProtocolExtensionContainer	{ { QoS-Flow-Mapping-Item-ExtIEs } }	OPTIONAL,
	...
}

QoS-Flow-Mapping-Item-ExtIEs		E1AP-PROTOCOL-EXTENSION ::= {
	...
}

QoS-Flow-Mapping-Indication ::= ENUMERATED {ul, dl, ...}

QoS-Parameters-Support-List	::= SEQUENCE {
	eUTRAN-QoS-Support-List			EUTRAN-QoS-Support-List			OPTIONAL,
	nG-RAN-QoS-Support-List			NG-RAN-QoS-Support-List			OPTIONAL,
	iE-Extensions					ProtocolExtensionContainer { { QoS-Parameters-Support-List-ItemExtIEs} } OPTIONAL,
	...
}

QoS-Parameters-Support-List-ItemExtIEs E1AP-PROTOCOL-EXTENSION ::= {
	...
}

QoSPriorityLevel ::= INTEGER (0..127, ...)


QoS-Flow-QoS-Parameter-List	::= SEQUENCE (SIZE(1.. maxnoofQoSFlows)) OF QoS-Flow-QoS-Parameter-Item

QoS-Flow-QoS-Parameter-Item	::=	SEQUENCE {
	qoS-Flow-Identifier						QoS-Flow-Identifier,
	qoSFlowLevelQoSParameters				QoSFlowLevelQoSParameters,
	qoSFlowMappingIndication				QoS-Flow-Mapping-Indication		OPTIONAL,
	iE-Extensions							ProtocolExtensionContainer	{ { QoS-Flow-QoS-Parameter-Item-ExtIEs } }	OPTIONAL,
	...
}

QoS-Flow-QoS-Parameter-Item-ExtIEs		E1AP-PROTOCOL-EXTENSION ::= {
	...
}

QoSFlowLevelQoSParameters	::= SEQUENCE {
	qoS-Characteristics						QoS-Characteristics,
	nGRANallocationRetentionPriority		NGRANAllocationAndRetentionPriority,
	gBR-QoS-Flow-Information				GBR-QoSFlowInformation						OPTIONAL,
	reflective-QoS-Attribute				ENUMERATED {subject-to, ...}				OPTIONAL,
	additional-QoS-Information				ENUMERATED {more-likely, ...}				OPTIONAL,
	paging-Policy-Indicator					INTEGER	(1..8,	...)						OPTIONAL,
	reflective-QoS-Indicator				ENUMERATED {enabled, ...}					OPTIONAL,
	iE-Extensions							ProtocolExtensionContainer { { QoSFlowLevelQoSParameters-ExtIEs } }	OPTIONAL
}

QoSFlowLevelQoSParameters-ExtIEs 	E1AP-PROTOCOL-EXTENSION ::= {
	...
}



RANUEID ::= OCTET STRING (SIZE (8))

RAT-Type	::=	ENUMERATED	{
	e-UTRA,
	nR,
	...
}

RLC-Mode	::=	ENUMERATED	{
	rlc-tm,
	rlc-am,
	rlc-um-bidirectional,
	rlc-um-unidirectional-ul,
	rlc-um-unidirectional-dl,
	...
}


ROHC-Parameters	::= CHOICE {
	rOHC					ROHC,
	uPlinkOnlyROHC			UplinkOnlyROHC,
	choice-Extension		ProtocolIE-SingleContainer { { ROHC-Parameters-ExtIEs} } 
}

ROHC-Parameters-ExtIEs E1AP-PROTOCOL-IES ::= {
	...
}

ROHC	::= SEQUENCE {
	maxCID							INTEGER (0..16383, ...),
	rOHC-Profiles					INTEGER (0..511, ...),
	continueROHC					ENUMERATED {true, ...}								OPTIONAL,
	iE-Extensions					ProtocolExtensionContainer { { ROHC-ExtIEs } } 		OPTIONAL
}

ROHC-ExtIEs E1AP-PROTOCOL-EXTENSION ::= {
	...
}




SecurityAlgorithm	::= SEQUENCE {
	cipheringAlgorithm				CipheringAlgorithm,
	integrityProtectionAlgorithm	IntegrityProtectionAlgorithm	OPTIONAL,
	iE-Extensions					ProtocolExtensionContainer { { SecurityAlgorithm-ExtIEs } }	OPTIONAL,
	...
}

SecurityAlgorithm-ExtIEs	E1AP-PROTOCOL-EXTENSION ::= {
	...
}

SecurityIndication ::= SEQUENCE {
	integrityProtectionIndication			IntegrityProtectionIndication,
	confidentialityProtectionIndication		ConfidentialityProtectionIndication,
	maximumIPdatarate							MaximumIPdatarate							OPTIONAL,
	iE-Extensions		ProtocolExtensionContainer { {SecurityIndication-ExtIEs} }	OPTIONAL,
	...
}

SecurityIndication-ExtIEs E1AP-PROTOCOL-EXTENSION ::= {
	...
}
	
SecurityInformation ::= SEQUENCE {
	securityAlgorithm			SecurityAlgorithm,
	uPSecuritykey				UPSecuritykey,
	iE-Extensions				ProtocolExtensionContainer { { SecurityInformation-ExtIEs } }	OPTIONAL,
	...
}

SecurityInformation-ExtIEs	E1AP-PROTOCOL-EXTENSION ::= {
	...
}

SecurityResult ::= SEQUENCE {
	integrityProtectionResult			IntegrityProtectionResult,
	confidentialityProtectionResult		ConfidentialityProtectionResult,
	iE-Extensions						ProtocolExtensionContainer { {SecurityResult-ExtIEs} }	OPTIONAL,
	...
}

SecurityResult-ExtIEs E1AP-PROTOCOL-EXTENSION ::= {
	...
}

Slice-Support-List ::= SEQUENCE (SIZE(1.. maxnoofSliceItems)) OF Slice-Support-Item

Slice-Support-Item ::= SEQUENCE {
	sNSSAI	SNSSAI,
	iE-Extensions				ProtocolExtensionContainer { { Slice-Support-Item-ExtIEs } }	OPTIONAL
}

Slice-Support-Item-ExtIEs	E1AP-PROTOCOL-EXTENSION ::= {
	...
}

SNSSAI ::= SEQUENCE {
	sST			OCTET STRING (SIZE(1)),
	sD			OCTET STRING (SIZE(3)) 	OPTIONAL,
	iE-Extensions				ProtocolExtensionContainer { { SNSSAI-ExtIEs } }	OPTIONAL,
	...
}

SNSSAI-ExtIEs	E1AP-PROTOCOL-EXTENSION ::= {
	...
}

SDAP-Configuration ::= SEQUENCE {
	defaultDRB				DefaultDRB,
	sDAP-Header-UL			SDAP-Header-UL,
	sDAP-Header-DL			SDAP-Header-DL,
	iE-Extensions			ProtocolExtensionContainer { { SDAP-Configuration-ExtIEs } }	OPTIONAL,
	...
}

SDAP-Configuration-ExtIEs	E1AP-PROTOCOL-EXTENSION ::= {
	...
}

SDAP-Header-DL	::=	ENUMERATED	{
	present,
	absent,
	...
}

SDAP-Header-UL	::=	ENUMERATED	{
	present,
	absent,
	...
}



TimeToWait ::= ENUMERATED {v1s, v2s, v5s, v10s, v20s, v60s, ...} 

TNLAssociationUsage ::= ENUMERATED {
	ue,
	non-ue,
	both, 
...
}


TransportLayerAddress		::= 	BIT STRING (SIZE(1..160, ...))

TransactionID				::= INTEGER (0..255, ...)

T-Reordering	::=	ENUMERATED	{ms0, ms1, ms2, ms4, ms5, ms8, ms10, ms15, ms20, ms30, ms40, ms50, ms60, ms80, ms100, ms120, ms140, ms160, ms180, ms200, ms220, ms240, ms260, ms280, ms300, ms500, ms750, ms1000, ms1250, ms1500, ms1750, ms2000, ms2250, ms2500, ms2750, ms3000, ...}

T-ReorderingTimer ::= SEQUENCE {
	t-Reordering				T-Reordering,
		iE-Extensions				ProtocolExtensionContainer { { T-ReorderingTimer-ExtIEs } }	OPTIONAL,
	...
}

T-ReorderingTimer-ExtIEs	E1AP-PROTOCOL-EXTENSION ::= {
	...
}

TypeOfError ::= ENUMERATED {
	not-understood,
	missing,
	...
}



UE-Activity	::=	ENUMERATED	{
	active,
	not-active,
	...
}

UE-associatedLogicalE1-ConnectionItem ::= SEQUENCE {
	gNB-CU-CP-UE-E1AP-ID		GNB-CU-CP-UE-E1AP-ID	 OPTIONAL,
	gNB-CU-UP-UE-E1AP-ID		GNB-CU-UP-UE-E1AP-ID	 OPTIONAL,
	iE-Extensions				ProtocolExtensionContainer { { UE-associatedLogicalE1-ConnectionItemExtIEs} }	OPTIONAL,
	...
}

UE-associatedLogicalE1-ConnectionItemExtIEs E1AP-PROTOCOL-EXTENSION ::= {
	...
}

UL-Configuration	::=	ENUMERATED	{
	no-data,
	shared,
	only,
	...
}

ULDataSplitThreshold	::=	ENUMERATED {b0, b100, b200, b400, b800, b1600, b3200, b6400, b12800, b25600, b51200, b102400, b204800, b409600, b819200, b1228800, b1638400, b2457600, b3276800, b4096000, b4915200, b5734400, b6553600, infinity, ...}

UP-Parameters ::= SEQUENCE (SIZE(1.. maxnoofUPParameters)) OF UP-Parameters-Item

UP-Parameters-Item ::= SEQUENCE {
	uP-TNL-Information			UP-TNL-Information,
	cell-Group-ID				Cell-Group-ID,
	iE-Extensions				ProtocolExtensionContainer { { UP-Parameters-Item-ExtIEs } }	OPTIONAL,
	...
}

UP-Parameters-Item-ExtIEs	E1AP-PROTOCOL-EXTENSION ::= {
	...
}

UPSecuritykey	::= SEQUENCE {
	encryptionKey				EncryptionKey,
	integrityProtectionKey		IntegrityProtectionKey		OPTIONAL,
	iE-Extensions				ProtocolExtensionContainer { { UPSecuritykey-ExtIEs } }	OPTIONAL,
	...
}

UPSecuritykey-ExtIEs	E1AP-PROTOCOL-EXTENSION ::= {
	...
}

UP-TNL-Information		::= 	CHOICE {
	gTPTunnel		GTPTunnel,
	choice-extension		ProtocolIE-SingleContainer	{{UP-TNL-Information-ExtIEs}}
}

UP-TNL-Information-ExtIEs E1AP-PROTOCOL-IES ::= {
	...
}

UplinkOnlyROHC ::= SEQUENCE {
	maxCID							INTEGER (0..16383, ...),
	rOHC-Profiles					INTEGER (0..511, ...),
	continueROHC					ENUMERATED {true, ...}	OPTIONAL,
	iE-Extensions					ProtocolExtensionContainer { { UplinkOnlyROHC-ExtIEs } } 		OPTIONAL
}

UplinkOnlyROHC-ExtIEs E1AP-PROTOCOL-EXTENSION ::= {
	...
}












END







E1AP-CommonDataTypes {
itu-t (0) identified-organization (4) etsi (0) mobileDomain (0)
ngran-access (22) modules (3) e1ap (5) version1 (1) e1ap-CommonDataTypes (3)}


DEFINITIONS AUTOMATIC TAGS ::= 

BEGIN








maxPrivateIEs 									INTEGER ::= 65535
maxProtocolExtensions 							INTEGER ::= 65535
maxProtocolIEs									INTEGER ::= 65535







Criticality		::= 	ENUMERATED { reject, ignore, notify }

Presence		::= ENUMERATED { optional, conditional, mandatory }

PrivateIE-ID	::= CHOICE {
	local				INTEGER (0.. maxPrivateIEs),
	global			OBJECT IDENTIFIER
}

ProcedureCode		::= INTEGER (0..255)

ProtocolExtensionID	::= INTEGER (0..maxProtocolExtensions)

ProtocolIE-ID		::= INTEGER (0..maxProtocolIEs)

TriggeringMessage	::= ENUMERATED { initiating-message, successful-outcome, unsuccessful-outcome}

END








E1AP-Constants {
itu-t (0) identified-organization (4) etsi (0) mobileDomain (0)
ngran-access (22) modules (3) e1ap (5) version1 (1) e1ap-Constants (4) }

DEFINITIONS AUTOMATIC TAGS ::= 

BEGIN

IMPORTS

	ProcedureCode,
	ProtocolIE-ID

FROM E1AP-CommonDataTypes;







id-reset														ProcedureCode ::= 0
id-errorIndication												ProcedureCode ::= 1
id-privateMessage												ProcedureCode ::= 2
id-gNB-CU-UP-E1Setup											ProcedureCode ::= 3
id-gNB-CU-CP-E1Setup											ProcedureCode ::= 4
id-gNB-CU-UP-ConfigurationUpdate								ProcedureCode ::= 5
id-gNB-CU-CP-ConfigurationUpdate								ProcedureCode ::= 6
id-e1Release													ProcedureCode ::= 7
id-bearerContextSetup											ProcedureCode ::= 8
id-bearerContextModification									ProcedureCode ::= 9
id-bearerContextModificationRequired							ProcedureCode ::= 10
id-bearerContextRelease											ProcedureCode ::= 11
id-bearerContextReleaseRequest									ProcedureCode ::= 12
id-bearerContextInactivityNotification							ProcedureCode ::= 13
id-dLDataNotification											ProcedureCode ::= 14
id-dataUsageReport												ProcedureCode ::= 15
id-gNB-CU-UP-CounterCheck										ProcedureCode ::= 16
id-gNB-CU-UP-StatusIndication									ProcedureCode ::= 17
id-uLDataNotification											ProcedureCode ::= 18
id-mRDC-DataUsageReport											ProcedureCode ::= 19








maxnoofErrors								INTEGER ::= 256
maxnoofSPLMNs								INTEGER ::= 12
maxnoofSliceItems							INTEGER ::= 1024
maxnoofIndividualE1ConnectionsToReset		INTEGER ::= 65536
maxnoofEUTRANQOSParameters					INTEGER ::= 256
maxnoofNGRANQOSParameters					INTEGER ::= 256
maxnoofDRBs									INTEGER	::= 32
maxnoofNRCGI								INTEGER	::= 512
maxnoofPDUSessionResource					INTEGER	::= 256
maxnoofQoSFlows								INTEGER	::= 64
maxnoofUPParameters							INTEGER	::= 8
maxnoofCellGroups							INTEGER	::= 4
maxnooftimeperiods							INTEGER	::= 2
maxnoofTNLAssociations						INTEGER ::= 32








id-Cause														ProtocolIE-ID ::= 0
id-CriticalityDiagnostics										ProtocolIE-ID ::= 1
id-gNB-CU-CP-UE-E1AP-ID 										ProtocolIE-ID ::= 2
id-gNB-CU-UP-UE-E1AP-ID											ProtocolIE-ID ::= 3
id-ResetType													ProtocolIE-ID ::= 4
id-UE-associatedLogicalE1-ConnectionItem						ProtocolIE-ID ::= 5
id-UE-associatedLogicalE1-ConnectionListResAck					ProtocolIE-ID ::= 6
id-gNB-CU-UP-ID													ProtocolIE-ID ::= 7
id-gNB-CU-UP-Name												ProtocolIE-ID ::= 8
id-gNB-CU-CP-Name												ProtocolIE-ID ::= 9
id-CNSupport													ProtocolIE-ID ::= 10
id-SupportedPLMNs												ProtocolIE-ID ::= 11
id-TimeToWait													ProtocolIE-ID ::= 12
id-SecurityInformation											ProtocolIE-ID ::= 13
id-UEDLAggregateMaximumBitRate									ProtocolIE-ID ::= 14
id-System-BearerContextSetupRequest								ProtocolIE-ID ::= 15
id-System-BearerContextSetupResponse							ProtocolIE-ID ::= 16
id-BearerContextStatusChange									ProtocolIE-ID ::= 17
id-System-BearerContextModificationRequest						ProtocolIE-ID ::= 18
id-System-BearerContextModificationResponse						ProtocolIE-ID ::= 19
id-System-BearerContextModificationConfirm						ProtocolIE-ID ::= 20
id-System-BearerContextModificationRequired						ProtocolIE-ID ::= 21
id-DRB-Status-List												ProtocolIE-ID ::= 22
id-ActivityNotificationLevel									ProtocolIE-ID ::= 23
id-ActivityInformation											ProtocolIE-ID ::= 24
id-Data-Usage-Report-List										ProtocolIE-ID ::= 25
id-New-UL-TNL-Information-Required								ProtocolIE-ID ::= 26
id-GNB-CU-CP-TNLA-To-Add-List									ProtocolIE-ID ::= 27
id-GNB-CU-CP-TNLA-To-Remove-List								ProtocolIE-ID ::= 28
id-GNB-CU-CP-TNLA-To-Update-List								ProtocolIE-ID ::= 29
id-GNB-CU-CP-TNLA-Setup-List									ProtocolIE-ID ::= 30
id-GNB-CU-CP-TNLA-Failed-To-Setup-List							ProtocolIE-ID ::= 31
id-DRB-To-Setup-List-EUTRAN										ProtocolIE-ID ::= 32
id-DRB-To-Modify-List-EUTRAN									ProtocolIE-ID ::= 33
id-DRB-To-Remove-List-EUTRAN									ProtocolIE-ID ::= 34
id-DRB-Required-To-Modify-List-EUTRAN							ProtocolIE-ID ::= 35
id-DRB-Required-To-Remove-List-EUTRAN							ProtocolIE-ID ::= 36
id-DRB-Setup-List-EUTRAN										ProtocolIE-ID ::= 37
id-DRB-Failed-List-EUTRAN										ProtocolIE-ID ::= 38
id-DRB-Modified-List-EUTRAN										ProtocolIE-ID ::= 39
id-DRB-Failed-To-Modify-List-EUTRAN								ProtocolIE-ID ::= 40
id-DRB-Confirm-Modified-List-EUTRAN								ProtocolIE-ID ::= 41
id-PDU-Session-Resource-To-Setup-List							ProtocolIE-ID ::= 42
id-PDU-Session-Resource-To-Modify-List							ProtocolIE-ID ::= 43
id-PDU-Session-Resource-To-Remove-List							ProtocolIE-ID ::= 44
id-PDU-Session-Resource-Required-To-Modify-List					ProtocolIE-ID ::= 45
id-PDU-Session-Resource-Setup-List								ProtocolIE-ID ::= 46
id-PDU-Session-Resource-Failed-List								ProtocolIE-ID ::= 47
id-PDU-Session-Resource-Modified-List							ProtocolIE-ID ::= 48
id-PDU-Session-Resource-Failed-To-Modify-List					ProtocolIE-ID ::= 49
id-PDU-Session-Resource-Confirm-Modified-List					ProtocolIE-ID ::= 50
id-DRB-To-Setup-Mod-List-EUTRAN									ProtocolIE-ID ::= 51
id-DRB-Setup-Mod-List-EUTRAN									ProtocolIE-ID ::= 52
id-DRB-Failed-Mod-List-EUTRAN									ProtocolIE-ID ::= 53
id-PDU-Session-Resource-Setup-Mod-List							ProtocolIE-ID ::= 54
id-PDU-Session-Resource-Failed-Mod-List							ProtocolIE-ID ::= 55
id-PDU-Session-Resource-To-Setup-Mod-List						ProtocolIE-ID ::= 56
id-TransactionID												ProtocolIE-ID ::= 57
id-Serving-PLMN													ProtocolIE-ID ::= 58
id-UE-Inactivity-Timer											ProtocolIE-ID ::= 59
id-System-GNB-CU-UP-CounterCheckRequest							ProtocolIE-ID ::= 60
id-DRBs-Subject-To-Counter-Check-List-EUTRAN					ProtocolIE-ID ::= 61
id-DRBs-Subject-To-Counter-Check-List-NG-RAN					ProtocolIE-ID ::= 62
id-PPI															ProtocolIE-ID ::= 63
id-gNB-CU-UP-Capacity											ProtocolIE-ID ::= 64
id-GNB-CU-UP-OverloadInformation								ProtocolIE-ID ::= 65
id-UEDLMaximumIntegrityProtectedDataRate						ProtocolIE-ID ::= 66
id-PDU-Session-To-Notify-List									ProtocolIE-ID ::= 67
id-PDU-Session-Resource-Data-Usage-List							ProtocolIE-ID ::= 68
id-SNSSAI														ProtocolIE-ID ::= 69
id-DataDiscardRequired										ProtocolIE-ID ::= 70
id-OldQoSFlowMap-ULendmarkerexpected							ProtocolIE-ID ::= 71
id-DRB-QoS															ProtocolIE-ID ::= 72
id-GNB-CU-UP-TNLA-To-Remove-List								ProtocolIE-ID ::= 73
id-endpoint-IP-Address-and-Port									ProtocolIE-ID ::= 74
id-TNLAssociationTransportLayerAddressgNBCUUP					ProtocolIE-ID ::= 75
id-RANUEID													ProtocolIE-ID ::= 76
id-GNB-DU-ID													ProtocolIE-ID ::= 77
id-CommonNetworkInstance											ProtocolIE-ID ::= 78
id-NetworkInstance												ProtocolIE-ID ::= 79
id-QoSFlowMappingIndication									ProtocolIE-ID ::= 80


END







E1AP-Containers {
itu-t (0) identified-organization (4) etsi (0) mobileDomain (0)
ngran-access (22) modules (3) e1ap (5) version1 (1) e1ap-Containers (5) }


DEFINITIONS AUTOMATIC TAGS ::= 

BEGIN







IMPORTS
	maxPrivateIEs,
	maxProtocolExtensions,
	maxProtocolIEs,
	Criticality,
	Presence,
	PrivateIE-ID,
	ProtocolIE-ID
	
FROM E1AP-CommonDataTypes;







E1AP-PROTOCOL-IES ::= CLASS {
	&id					ProtocolIE-ID			UNIQUE,
	&criticality		Criticality,
	&Value,
	&presence			Presence
}
WITH SYNTAX {
	ID					&id
	CRITICALITY			&criticality
	TYPE				&Value
	PRESENCE			&presence
}







E1AP-PROTOCOL-EXTENSION ::= CLASS {
	&id					ProtocolIE-ID		UNIQUE,
	&criticality		Criticality,
	&Extension,
	&presence			Presence
}
WITH SYNTAX {
	ID					&id
	CRITICALITY			&criticality
	EXTENSION			&Extension
	PRESENCE			&presence
}







E1AP-PRIVATE-IES ::= CLASS {
	&id					PrivateIE-ID,
	&criticality		Criticality,
	&Value,
	&presence			Presence
}
WITH SYNTAX {
	ID					&id
	CRITICALITY			&criticality
	TYPE				&Value
	PRESENCE			&presence
}







ProtocolIE-Container { E1AP-PROTOCOL-IES : IEsSetParam} ::= 
	SEQUENCE (SIZE (0..maxProtocolIEs)) OF
	ProtocolIE-Field {{IEsSetParam}}

ProtocolIE-SingleContainer { E1AP-PROTOCOL-IES : IEsSetParam} ::= 
	ProtocolIE-Field {{IEsSetParam}}

ProtocolIE-Field { E1AP-PROTOCOL-IES : IEsSetParam} ::= SEQUENCE {
	id				E1AP-PROTOCOL-IES.&id				({IEsSetParam}),
	criticality		E1AP-PROTOCOL-IES.&criticality		({IEsSetParam}{@id}),
	value			E1AP-PROTOCOL-IES.&Value			({IEsSetParam}{@id})
}







ProtocolIE-ContainerList {INTEGER : lowerBound, INTEGER : upperBound, E1AP-PROTOCOL-IES : IEsSetParam} ::=
	SEQUENCE (SIZE (lowerBound..upperBound)) OF
	ProtocolIE-Container {{IEsSetParam}}







ProtocolExtensionContainer { E1AP-PROTOCOL-EXTENSION : ExtensionSetParam} ::= 
	SEQUENCE (SIZE (1..maxProtocolExtensions)) OF
	ProtocolExtensionField {{ExtensionSetParam}}

ProtocolExtensionField { E1AP-PROTOCOL-EXTENSION : ExtensionSetParam} ::= SEQUENCE {
	id					E1AP-PROTOCOL-EXTENSION.&id				({ExtensionSetParam}),
	criticality			E1AP-PROTOCOL-EXTENSION.&criticality	({ExtensionSetParam}{@id}),
	extensionValue		E1AP-PROTOCOL-EXTENSION.&Extension		({ExtensionSetParam}{@id})
}







PrivateIE-Container { E1AP-PRIVATE-IES : IEsSetParam} ::= 
	SEQUENCE (SIZE (1..maxPrivateIEs)) OF
	PrivateIE-Field {{IEsSetParam}}

PrivateIE-Field { E1AP-PRIVATE-IES : IEsSetParam} ::= SEQUENCE {
	id				E1AP-PRIVATE-IES.&id				({IEsSetParam}),
	criticality		E1AP-PRIVATE-IES.&criticality		({IEsSetParam}{@id}),
	value			E1AP-PRIVATE-IES.&Value			({IEsSetParam}{@id})
}

END
