XnAP-PDU-Descriptions {
itu-t (0) identified-organization (4) etsi (0) mobileDomain (0)
ngran-access (22) modules (3) xnap (2) version1 (1) xnap-PDU-Descriptions (0) }

DEFINITIONS AUTOMATIC TAGS ::=

BEGIN






IMPORTS
	Criticality, 
	ProcedureCode

FROM XnAP-CommonDataTypes

	HandoverRequest, 
	HandoverRequestAcknowledge, 
	HandoverPreparationFailure, 
	SNStatusTransfer, 
	UEContextRelease, 
	HandoverCancel, 
	NotificationControlIndication, 
	RANPaging, 
	RetrieveUEContextRequest, 
	RetrieveUEContextResponse, 
	RetrieveUEContextFailure, 
	XnUAddressIndication, 
	SecondaryRATDataUsageReport, 
	SNodeAdditionRequest, 
	SNodeAdditionRequestAcknowledge, 
	SNodeAdditionRequestReject, 
	SNodeReconfigurationComplete, 
	SNodeModificationRequest, 
	SNodeModificationRequestAcknowledge, 
	SNodeModificationRequestReject, 
	SNodeModificationRequired, 
	SNodeModificationConfirm, 
	SNodeModificationRefuse, 
	SNodeReleaseRequest, 
	SNodeReleaseRequestAcknowledge, 
	SNodeReleaseReject, 
	SNodeReleaseRequired, 
	SNodeReleaseConfirm, 
	SNodeCounterCheckRequest, 
	SNodeChangeRequired, 
	SNodeChangeConfirm, 
	SNodeChangeRefuse, 
	RRCTransfer, 
	XnRemovalRequest, 
	XnRemovalResponse, 
	XnRemovalFailure, 
	XnSetupRequest, 
	XnSetupResponse, 
	XnSetupFailure, 
	NGRANNodeConfigurationUpdate, 
	NGRANNodeConfigurationUpdateAcknowledge, 
	NGRANNodeConfigurationUpdateFailure, 
	E-UTRA-NR-CellResourceCoordinationRequest, 
	E-UTRA-NR-CellResourceCoordinationResponse, 
	ActivityNotification, 
	CellActivationRequest, 
	CellActivationResponse, 
	CellActivationFailure, 
	ResetRequest, 
	ResetResponse, 
	ErrorIndication, 
	PrivateMessage, 
	DeactivateTrace, 
	TraceStart, 
	HandoverSuccess, 
	ConditionalHandoverCancel, 
	EarlyStatusTransfer, 
	FailureIndication, 
	HandoverReport, 
	ResourceStatusRequest, 
	ResourceStatusResponse, 
	ResourceStatusFailure, 
	ResourceStatusUpdate, 
	MobilityChangeRequest, 
	MobilityChangeAcknowledge, 
	MobilityChangeFailure, 
	AccessAndMobilityIndication


FROM XnAP-PDU-Contents

	id-handoverPreparation, 
	id-sNStatusTransfer, 
	id-handoverCancel, 
	id-notificationControl, 
	id-retrieveUEContext, 
	id-rANPaging, 
	id-xnUAddressIndication, 
	id-uEContextRelease, 
	id-secondaryRATDataUsageReport, 
	id-sNGRANnodeAdditionPreparation, 
	id-sNGRANnodeReconfigurationCompletion, 
	id-mNGRANnodeinitiatedSNGRANnodeModificationPreparation, 
	id-sNGRANnodeinitiatedSNGRANnodeModificationPreparation, 
	id-mNGRANnodeinitiatedSNGRANnodeRelease, 
	id-sNGRANnodeinitiatedSNGRANnodeRelease, 
	id-sNGRANnodeCounterCheck, 
	id-sNGRANnodeChange, 
	id-activityNotification, 
	id-rRCTransfer, 
	id-xnRemoval, 
	id-xnSetup, 
	id-nGRANnodeConfigurationUpdate, 
	id-e-UTRA-NR-CellResourceCoordination, 
	id-cellActivation, 
	id-reset, 
	id-errorIndication, 
	id-privateMessage, 
	id-deactivateTrace, 
	id-traceStart, 
	id-handoverSuccess, 
	id-conditionalHandoverCancel, 
	id-earlyStatusTransfer, 
	id-failureIndication, 
	id-handoverReport, 
	id-resourceStatusReportingInitiation, 
	id-resourceStatusReporting, 
	id-mobilitySettingsChange, 
	id-accessAndMobilityIndication

FROM XnAP-Constants;






XNAP-ELEMENTARY-PROCEDURE ::= CLASS {
	&InitiatingMessage				, 
	&SuccessfulOutcome				OPTIONAL, 
	&UnsuccessfulOutcome				OPTIONAL, 
	&procedureCode			ProcedureCode	UNIQUE, 
	&criticality			Criticality		DEFAULT ignore
}
WITH SYNTAX {
	INITIATING MESSAGE		&InitiatingMessage
	[SUCCESSFUL OUTCOME		&SuccessfulOutcome]
	[UNSUCCESSFUL OUTCOME		&UnsuccessfulOutcome]
	PROCEDURE CODE			&procedureCode
	[CRITICALITY			&criticality]
}






XnAP-PDU ::= CHOICE {
	initiatingMessage	InitiatingMessage, 
	successfulOutcome	SuccessfulOutcome, 
	unsuccessfulOutcome	UnsuccessfulOutcome, 
	...
}

InitiatingMessage ::= SEQUENCE {
	procedureCode	XNAP-ELEMENTARY-PROCEDURE.&procedureCode		({XNAP-ELEMENTARY-PROCEDURES}), 
	criticality		XNAP-ELEMENTARY-PROCEDURE.&criticality			({XNAP-ELEMENTARY-PROCEDURES}{@procedureCode}), 
	value			XNAP-ELEMENTARY-PROCEDURE.&InitiatingMessage	({XNAP-ELEMENTARY-PROCEDURES}{@procedureCode})
}

SuccessfulOutcome ::= SEQUENCE {
	procedureCode	XNAP-ELEMENTARY-PROCEDURE.&procedureCode		({XNAP-ELEMENTARY-PROCEDURES}), 
	criticality		XNAP-ELEMENTARY-PROCEDURE.&criticality			({XNAP-ELEMENTARY-PROCEDURES}{@procedureCode}), 
	value			XNAP-ELEMENTARY-PROCEDURE.&SuccessfulOutcome	({XNAP-ELEMENTARY-PROCEDURES}{@procedureCode})
}

UnsuccessfulOutcome ::= SEQUENCE {
	procedureCode	XNAP-ELEMENTARY-PROCEDURE.&procedureCode		({XNAP-ELEMENTARY-PROCEDURES}), 
	criticality		XNAP-ELEMENTARY-PROCEDURE.&criticality			({XNAP-ELEMENTARY-PROCEDURES}{@procedureCode}), 
	value			XNAP-ELEMENTARY-PROCEDURE.&UnsuccessfulOutcome	({XNAP-ELEMENTARY-PROCEDURES}{@procedureCode})
}






XNAP-ELEMENTARY-PROCEDURES XNAP-ELEMENTARY-PROCEDURE ::= {
	XNAP-ELEMENTARY-PROCEDURES-CLASS-1			|
	XNAP-ELEMENTARY-PROCEDURES-CLASS-2			, 
	...
}

XNAP-ELEMENTARY-PROCEDURES-CLASS-1 XNAP-ELEMENTARY-PROCEDURE ::= {
	handoverPreparation										|
	retrieveUEContext										|
	sNGRANnodeAdditionPreparation							|
	mNGRANnodeinitiatedSNGRANnodeModificationPreparation	|
	sNGRANnodeinitiatedSNGRANnodeModificationPreparation	|
	mNGRANnodeinitiatedSNGRANnodeRelease					|
	sNGRANnodeinitiatedSNGRANnodeRelease					|
	sNGRANnodeChange										|
	xnRemoval												|
	xnSetup													|
	nGRANnodeConfigurationUpdate							|
	e-UTRA-NR-CellResourceCoordination						|
	cellActivation											|
	reset													|
	resourceStatusReportingInitiation						|
	mobilitySettingsChange									, 
	...
}

XNAP-ELEMENTARY-PROCEDURES-CLASS-2 XNAP-ELEMENTARY-PROCEDURE ::= {
	sNStatusTransfer						|
	handoverCancel							|
	rANPaging								|
	xnUAddressIndication					|
	uEContextRelease						|
	sNGRANnodeReconfigurationCompletion		|
	sNGRANnodeCounterCheck					|
	rRCTransfer								|
	errorIndication							|
	privateMessage							|
	notificationControl						|
	activityNotification					|
	secondaryRATDataUsageReport 			|
	deactivateTrace							|
	traceStart								|
	handoverSuccess							|
	conditionalHandoverCancel				|
	earlyStatusTransfer						|
	failureIndication						|
	handoverReport							|
	resourceStatusReporting					|
	accessAndMobilityIndication				, 
	...

}






handoverPreparation	XNAP-ELEMENTARY-PROCEDURE ::= {
	INITIATING MESSAGE		HandoverRequest
	SUCCESSFUL OUTCOME		HandoverRequestAcknowledge
	UNSUCCESSFUL OUTCOME	HandoverPreparationFailure
	PROCEDURE CODE			id-handoverPreparation
	CRITICALITY				reject
}


sNStatusTransfer	XNAP-ELEMENTARY-PROCEDURE ::= {
	INITIATING MESSAGE		SNStatusTransfer
	PROCEDURE CODE			id-sNStatusTransfer
	CRITICALITY				ignore
}


handoverCancel	XNAP-ELEMENTARY-PROCEDURE ::= {
	INITIATING MESSAGE		HandoverCancel
	PROCEDURE CODE			id-handoverCancel
	CRITICALITY				ignore
}


retrieveUEContext	XNAP-ELEMENTARY-PROCEDURE ::= {
	INITIATING MESSAGE		RetrieveUEContextRequest
	SUCCESSFUL OUTCOME		RetrieveUEContextResponse
	UNSUCCESSFUL OUTCOME	RetrieveUEContextFailure
	PROCEDURE CODE			id-retrieveUEContext
	CRITICALITY				reject
}


rANPaging	XNAP-ELEMENTARY-PROCEDURE ::= {
	INITIATING MESSAGE		RANPaging
	PROCEDURE CODE			id-rANPaging
	CRITICALITY				reject
}


xnUAddressIndication	XNAP-ELEMENTARY-PROCEDURE ::= {
	INITIATING MESSAGE		XnUAddressIndication
	PROCEDURE CODE			id-xnUAddressIndication
	CRITICALITY				reject
}


uEContextRelease	XNAP-ELEMENTARY-PROCEDURE ::= {
	INITIATING MESSAGE		UEContextRelease
	PROCEDURE CODE			id-uEContextRelease
	CRITICALITY				reject
}


sNGRANnodeAdditionPreparation	XNAP-ELEMENTARY-PROCEDURE ::= {
	INITIATING MESSAGE		SNodeAdditionRequest
	SUCCESSFUL OUTCOME		SNodeAdditionRequestAcknowledge
	UNSUCCESSFUL OUTCOME	SNodeAdditionRequestReject
	PROCEDURE CODE			id-sNGRANnodeAdditionPreparation
	CRITICALITY				reject
}


sNGRANnodeReconfigurationCompletion	XNAP-ELEMENTARY-PROCEDURE ::= {
	INITIATING MESSAGE		SNodeReconfigurationComplete
	PROCEDURE CODE			id-sNGRANnodeReconfigurationCompletion
	CRITICALITY				reject
}


mNGRANnodeinitiatedSNGRANnodeModificationPreparation	XNAP-ELEMENTARY-PROCEDURE ::= {
	INITIATING MESSAGE		SNodeModificationRequest
	SUCCESSFUL OUTCOME		SNodeModificationRequestAcknowledge
	UNSUCCESSFUL OUTCOME	SNodeModificationRequestReject
	PROCEDURE CODE			id-mNGRANnodeinitiatedSNGRANnodeModificationPreparation
	CRITICALITY				reject
}


sNGRANnodeinitiatedSNGRANnodeModificationPreparation	XNAP-ELEMENTARY-PROCEDURE ::= {
	INITIATING MESSAGE		SNodeModificationRequired
	SUCCESSFUL OUTCOME		SNodeModificationConfirm
	UNSUCCESSFUL OUTCOME	SNodeModificationRefuse
	PROCEDURE CODE			id-sNGRANnodeinitiatedSNGRANnodeModificationPreparation
	CRITICALITY				reject
}


mNGRANnodeinitiatedSNGRANnodeRelease	XNAP-ELEMENTARY-PROCEDURE ::= {
	INITIATING MESSAGE		SNodeReleaseRequest
	SUCCESSFUL OUTCOME		SNodeReleaseRequestAcknowledge
	UNSUCCESSFUL OUTCOME	SNodeReleaseReject
	PROCEDURE CODE			id-mNGRANnodeinitiatedSNGRANnodeRelease
	CRITICALITY				reject
}


sNGRANnodeinitiatedSNGRANnodeRelease	XNAP-ELEMENTARY-PROCEDURE ::= {
	INITIATING MESSAGE		SNodeReleaseRequired
	SUCCESSFUL OUTCOME		SNodeReleaseConfirm
	PROCEDURE CODE			id-sNGRANnodeinitiatedSNGRANnodeRelease
	CRITICALITY				reject
}


sNGRANnodeCounterCheck	XNAP-ELEMENTARY-PROCEDURE ::= {
	INITIATING MESSAGE		SNodeCounterCheckRequest
	PROCEDURE CODE			id-sNGRANnodeCounterCheck
	CRITICALITY				reject
}


sNGRANnodeChange		XNAP-ELEMENTARY-PROCEDURE ::= {
	INITIATING MESSAGE		SNodeChangeRequired
	SUCCESSFUL OUTCOME		SNodeChangeConfirm
	UNSUCCESSFUL OUTCOME	SNodeChangeRefuse
	PROCEDURE CODE			id-sNGRANnodeChange
	CRITICALITY				reject
}


rRCTransfer	XNAP-ELEMENTARY-PROCEDURE ::= {
	INITIATING MESSAGE		RRCTransfer
	PROCEDURE CODE			id-rRCTransfer
	CRITICALITY				reject
}


xnRemoval	XNAP-ELEMENTARY-PROCEDURE ::= {
	INITIATING MESSAGE		XnRemovalRequest
	SUCCESSFUL OUTCOME		XnRemovalResponse
	UNSUCCESSFUL OUTCOME		XnRemovalFailure
	PROCEDURE CODE			id-xnRemoval
	CRITICALITY				reject
}


xnSetup	XNAP-ELEMENTARY-PROCEDURE ::= {
	INITIATING MESSAGE		XnSetupRequest
	SUCCESSFUL OUTCOME		XnSetupResponse
	UNSUCCESSFUL OUTCOME		XnSetupFailure
	PROCEDURE CODE			id-xnSetup
	CRITICALITY				reject
}


nGRANnodeConfigurationUpdate	XNAP-ELEMENTARY-PROCEDURE ::= {
	INITIATING MESSAGE		NGRANNodeConfigurationUpdate
	SUCCESSFUL OUTCOME		NGRANNodeConfigurationUpdateAcknowledge
	UNSUCCESSFUL OUTCOME	NGRANNodeConfigurationUpdateFailure
	PROCEDURE CODE			id-nGRANnodeConfigurationUpdate
	CRITICALITY				reject
}


e-UTRA-NR-CellResourceCoordination	XNAP-ELEMENTARY-PROCEDURE ::= {
	INITIATING MESSAGE		E-UTRA-NR-CellResourceCoordinationRequest
	SUCCESSFUL OUTCOME		E-UTRA-NR-CellResourceCoordinationResponse
	PROCEDURE CODE			id-e-UTRA-NR-CellResourceCoordination
	CRITICALITY				reject
}


cellActivation	XNAP-ELEMENTARY-PROCEDURE ::= {
	INITIATING MESSAGE		CellActivationRequest
	SUCCESSFUL OUTCOME		CellActivationResponse
	UNSUCCESSFUL OUTCOME	CellActivationFailure
	PROCEDURE CODE			id-cellActivation
	CRITICALITY				reject
}


reset	XNAP-ELEMENTARY-PROCEDURE ::= {
	INITIATING MESSAGE		ResetRequest
	SUCCESSFUL OUTCOME		ResetResponse
	PROCEDURE CODE			id-reset
	CRITICALITY				reject
}


errorIndication	XNAP-ELEMENTARY-PROCEDURE ::= {
	INITIATING MESSAGE		ErrorIndication
	PROCEDURE CODE			id-errorIndication
	CRITICALITY				ignore
}


notificationControl			XNAP-ELEMENTARY-PROCEDURE ::= {
	INITIATING MESSAGE		NotificationControlIndication
	PROCEDURE CODE			id-notificationControl
	CRITICALITY				ignore
}


activityNotification		XNAP-ELEMENTARY-PROCEDURE ::= {
	INITIATING MESSAGE		ActivityNotification
	PROCEDURE CODE			id-activityNotification
	CRITICALITY				ignore
}


privateMessage			XNAP-ELEMENTARY-PROCEDURE ::= {
	INITIATING MESSAGE		PrivateMessage
	PROCEDURE CODE			id-privateMessage
	CRITICALITY				ignore
}

secondaryRATDataUsageReport	XNAP-ELEMENTARY-PROCEDURE ::= {
	INITIATING MESSAGE		SecondaryRATDataUsageReport
	PROCEDURE CODE			id-secondaryRATDataUsageReport
	CRITICALITY				reject
}

deactivateTrace XNAP-ELEMENTARY-PROCEDURE ::= {
	INITIATING MESSAGE		DeactivateTrace
	PROCEDURE CODE			id-deactivateTrace
	CRITICALITY				ignore
}

traceStart XNAP-ELEMENTARY-PROCEDURE ::= {
	INITIATING MESSAGE		TraceStart
	PROCEDURE CODE			id-traceStart
	CRITICALITY				ignore
}

handoverSuccess			XNAP-ELEMENTARY-PROCEDURE ::= {
	INITIATING MESSAGE		HandoverSuccess
	PROCEDURE CODE			id-handoverSuccess
	CRITICALITY				ignore
}

conditionalHandoverCancel	XNAP-ELEMENTARY-PROCEDURE ::= {
	INITIATING MESSAGE		ConditionalHandoverCancel
	PROCEDURE CODE			id-conditionalHandoverCancel
	CRITICALITY				ignore
}

earlyStatusTransfer		XNAP-ELEMENTARY-PROCEDURE ::= {
	INITIATING MESSAGE		EarlyStatusTransfer
	PROCEDURE CODE			id-earlyStatusTransfer
	CRITICALITY				ignore
}

failureIndication XNAP-ELEMENTARY-PROCEDURE ::= {
	INITIATING MESSAGE		FailureIndication
	PROCEDURE CODE			id-failureIndication
	CRITICALITY				ignore
}

handoverReport XNAP-ELEMENTARY-PROCEDURE ::= {
	INITIATING MESSAGE		HandoverReport
	PROCEDURE CODE			id-handoverReport
	CRITICALITY				ignore
}

resourceStatusReportingInitiation	XNAP-ELEMENTARY-PROCEDURE ::= {
	INITIATING MESSAGE				ResourceStatusRequest
	SUCCESSFUL OUTCOME				ResourceStatusResponse
	UNSUCCESSFUL OUTCOME			ResourceStatusFailure
	PROCEDURE CODE					id-resourceStatusReportingInitiation
	CRITICALITY						reject
}

resourceStatusReporting XNAP-ELEMENTARY-PROCEDURE ::= {
	INITIATING MESSAGE		ResourceStatusUpdate
	PROCEDURE CODE			id-resourceStatusReporting
	CRITICALITY				ignore
}

mobilitySettingsChange	XNAP-ELEMENTARY-PROCEDURE ::= {
	INITIATING MESSAGE				MobilityChangeRequest
	SUCCESSFUL OUTCOME				MobilityChangeAcknowledge
	UNSUCCESSFUL OUTCOME			MobilityChangeFailure
PROCEDURE CODE					id-mobilitySettingsChange
	CRITICALITY						reject
}


accessAndMobilityIndication XNAP-ELEMENTARY-PROCEDURE ::={
	INITIATING MESSAGE 		AccessAndMobilityIndication
	PROCEDURE CODE			id-accessAndMobilityIndication
	CRITICALITY 				ignore
}

END






XnAP-PDU-Contents {
itu-t (0) identified-organization (4) etsi (0) mobileDomain (0)
ngran-access (22) modules (3) xnap (2) version1 (1) xnap-PDU-Contents (1) }

DEFINITIONS AUTOMATIC TAGS ::=

BEGIN






IMPORTS

	ActivationIDforCellActivation, 
	AMF-Region-Information, 
	AMF-UE-NGAP-ID, 
	AS-SecurityInformation, 
	AssistanceDataForRANPaging, 
	BitRate, 
	Cause, 
	CellAndCapacityAssistanceInfo-EUTRA, 
	CellAndCapacityAssistanceInfo-NR, 
	CellAssistanceInfo-EUTRA, 
	CellAssistanceInfo-NR, 
	CHOinformation-Req, 
	CHOinformation-Ack, 
	CHO-MRDC-Indicator, 
	CPTransportLayerInformation, 
	TNLA-To-Add-List, 
	TNLA-To-Update-List, 
	TNLA-To-Remove-List, 
	TNLA-Setup-List, 
	TNLA-Failed-To-Setup-List, 
	CriticalityDiagnostics, 
	XnUAddressInfoperPDUSession-List, 
	DAPSResponseInfo-List, 
	DataTrafficResourceIndication, 
	DeliveryStatus, 
	DesiredActNotificationLevel, 
	DRB-ID, 
	DRB-List, 
	DRB-Number, 
	DRBsSubjectToDLDiscarding-List, 
	DRBsSubjectToEarlyStatusTransfer-List, 
	DRBsSubjectToStatusTransfer-List, 
	DRBToQoSFlowMapping-List, 
	E-UTRA-CGI, 
	ExpectedUEBehaviour, 
	FiveGCMobilityRestrictionListContainer, 
	GlobalNG-RANNode-ID, 
	GlobalNG-RANCell-ID, 
	GUAMI, 
	InterfaceInstanceIndication, 
	I-RNTI, 
	LocationInformationSNReporting, 
	LocationReportingInformation, 
	LowerLayerPresenceStatusChange, 
	LTEUESidelinkAggregateMaximumBitRate, 
	LTEV2XServicesAuthorized, 
	MR-DC-ResourceCoordinationInfo, 
	ServedCells-E-UTRA, 
	ServedCells-NR, 
	ServedCellsToUpdate-E-UTRA, 
	ServedCellsToUpdate-NR, 
	MAC-I, 
	MaskedIMEISV, 
	MDT-Configuration, 
	MDTPLMNList, 
	MobilityRestrictionList, 
	NG-RAN-Cell-Identity, 
	NG-RANnodeUEXnAPID, 
	NR-CGI, 
	NE-DC-TDM-Pattern, 
	NRUESidelinkAggregateMaximumBitRate, 
	NRV2XServicesAuthorized, 
	PagingDRX, 
	PagingPriority, 
	PartialListIndicator, 
	PLMN-Identity, 
	PDCPChangeIndication, 
	PDUSessionAggregateMaximumBitRate, 
	PDUSession-ID, 
	PDUSession-List, 
	PDUSession-List-withCause, 
	PDUSession-List-withDataForwardingFromTarget, 
	PDUSession-List-withDataForwardingRequest, 
	PDUSessionResourcesAdmitted-List, 
	PDUSessionResourcesNotAdmitted-List, 
	PDUSessionResourcesToBeSetup-List, 
	PDUSessionResourceChangeRequiredInfo-SNterminated, 
	PDUSessionResourceChangeRequiredInfo-MNterminated, 
	PDUSessionResourceChangeConfirmInfo-SNterminated, 
	PDUSessionResourceChangeConfirmInfo-MNterminated, 
	PDUSessionResourceSecondaryRATUsageList, 
	PDUSessionResourceSetupInfo-SNterminated, 
	PDUSessionResourceSetupInfo-MNterminated, 
	PDUSessionResourceSetupResponseInfo-SNterminated, 
	PDUSessionResourceSetupResponseInfo-MNterminated, 
	PDUSessionResourceModificationInfo-SNterminated, 
	PDUSessionResourceModificationInfo-MNterminated, 
	PDUSessionResourceModificationResponseInfo-SNterminated, 
	PDUSessionResourceModificationResponseInfo-MNterminated, 
	PDUSessionResourceModConfirmInfo-SNterminated, 
	PDUSessionResourceModConfirmInfo-MNterminated, 
	PDUSessionResourceModRqdInfo-SNterminated, 
	PDUSessionResourceModRqdInfo-MNterminated, 
	PDUSessionType, 
	PC5QoSParameters, 
	QoSFlowIdentifier, 
	QoSFlowNotificationControlIndicationInfo, 
	QoSFlows-List, 
	RANPagingArea, 
	ResetRequestTypeInfo, 
	ResetResponseTypeInfo, 
	RFSP-Index, 
	RRCConfigIndication, 
	RRCResumeCause, 
	SCGConfigurationQuery, 
	SecurityIndication, 
	S-NG-RANnode-SecurityKey, 
	SpectrumSharingGroupID, 
	SplitSRBsTypes, 
	S-NG-RANnode-Addition-Trigger-Ind, 
	S-NSSAI, 
	TargetCellList, 
	TAISupport-List, 
	Target-CGI, 
	TimeToWait, 
	TraceActivation, 
	UEAggregateMaximumBitRate, 
	UEContextID, 
	UEContextInfoRetrUECtxtResp, 
	UEContextKeptIndicator, 
	UEHistoryInformation, 
	UEIdentityIndexValue, 
	UERadioCapabilityForPaging, 
	UERadioCapabilityID, 
	UERANPagingIdentity, 
	UESecurityCapabilities, 
	UPTransportLayerInformation, 
	UserPlaneTrafficActivityReport, 
	XnBenefitValue, 
	RANPagingFailure, 
	TNLConfigurationInfo, 
	MaximumCellListSize, 
	MessageOversizeNotification, 
	NG-RANTraceID, 
	MobilityInformation, 
	InitiatingCondition-FailureIndication, 
	HandoverReportType, 
	TargetCellinEUTRAN, 
	C-RNTI, 
	UERLFReportContainer, 
	Measurement-ID, 
	RegistrationRequest, 
	ReportCharacteristics, 
	CellToReport, 
	ReportingPeriodicity, 
	CellMeasurementResult, 
	UEHistoryInformationFromTheUE, 
	MobilityParametersInformation, 
	MobilityParametersModificationRange, 
	RACHReportInformation, 
	IABNodeIndication, 
	SNTriggered


FROM XnAP-IEs

	PrivateIE-Container{}, 
	ProtocolExtensionContainer{}, 
	ProtocolIE-Container{}, 
	ProtocolIE-ContainerList{}, 
	ProtocolIE-ContainerPair{}, 
	ProtocolIE-ContainerPairList{}, 
	ProtocolIE-Single-Container{}, 
	XNAP-PRIVATE-IES, 
	XNAP-PROTOCOL-EXTENSION, 
	XNAP-PROTOCOL-IES, 
	XNAP-PROTOCOL-IES-PAIR
FROM XnAP-Containers


	id-ActivatedServedCells, 
	id-ActivationIDforCellActivation, 
	id-AdditionalDRBIDs, 
	id-AMF-Region-Information, 
	id-AMF-Region-Information-To-Add, 
	id-AMF-Region-Information-To-Delete, 
	id-AssistanceDataForRANPaging, 
	id-AvailableDRBIDs, 
	id-Cause, 
	id-cellAssistanceInfo-EUTRA, 
	id-cellAssistanceInfo-NR, 
	id-CellAndCapacityAssistanceInfo-EUTRA, 
	id-CellAndCapacityAssistanceInfo-NR, 
	id-ConfigurationUpdateInitiatingNodeChoice, 
	id-UEContextID, 
	id-CriticalityDiagnostics, 
	id-XnUAddressInfoperPDUSession-List, 
	id-DesiredActNotificationLevel, 
	id-DRBsSubjectToStatusTransfer-List, 
	id-ExpectedUEBehaviour, 
	id-FiveGCMobilityRestrictionListContainer, 
	id-GlobalNG-RAN-node-ID, 
	id-GUAMI, 
	id-indexToRatFrequSelectionPriority, 
	id-List-of-served-cells-E-UTRA, 
	id-List-of-served-cells-NR, 
	id-LocationInformationSN, 
	id-LocationInformationSNReporting, 
	id-LocationReportingInformation, 
	id-LTEUESidelinkAggregateMaximumBitRate, 
	id-LTEV2XServicesAuthorized, 
	id-MAC-I, 
	id-MaskedIMEISV, 
	id-MDT-Configuration, 
	id-MDTPLMNList, 
	id-MN-to-SN-Container, 
	id-MobilityRestrictionList, 
	id-M-NG-RANnodeUEXnAPID, 
	id-new-NG-RAN-Cell-Identity, 
	id-newNG-RANnodeUEXnAPID, 
	id-NRUESidelinkAggregateMaximumBitRate, 
	id-NRV2XServicesAuthorized, 
	id-oldNG-RANnodeUEXnAPID, 
	id-OldtoNewNG-RANnodeResumeContainer, 
	id-PagingDRX, 
	id-PagingPriority, 
	id-PartialListIndicator-EUTRA, 
	id-PartialListIndicator-NR, 
	id-PCellID, 
	id-PDUSessionResourceSecondaryRATUsageList, 
	id-PDUSessionResourcesActivityNotifyList, 
	id-PDUSessionResourcesAdmitted-List, 
	id-PDUSessionResourcesNotAdmitted-List, 
	id-PDUSessionResourcesNotifyList, 
	id-PDUSessionToBeAddedAddReq, 
	id-PDUSessionToBeReleased-RelReqAck, 
	id-procedureStage, 
	id-RANPagingArea, 
	id-requestedSplitSRB, 
	id-RequiredNumberOfDRBIDs, 
	id-ResetRequestTypeInfo, 
	id-ResetResponseTypeInfo, 
	id-RespondingNodeTypeConfigUpdateAck, 
	id-RRCResumeCause, 
	id-selectedPLMN, 
	id-ServedCellsToActivate, 
	id-servedCellsToUpdate-E-UTRA, 
	id-ServedCellsToUpdateInitiatingNodeChoice, 
	id-servedCellsToUpdate-NR, 
	id-sourceNG-RANnodeUEXnAPID, 
	id-SpareDRBIDs, 
	id-S-NG-RANnodeMaxIPDataRate-UL, 
	id-S-NG-RANnodeMaxIPDataRate-DL, 
	id-S-NG-RANnodeUEXnAPID, 
	id-TAISupport-list, 
	id-Target2SourceNG-RANnodeTranspContainer, 
	id-targetCellGlobalID, 
	id-targetNG-RANnodeUEXnAPID, 
	id-TimeToWait, 
	id-TNLA-To-Add-List, 
	id-TNLA-To-Update-List, 
	id-TNLA-To-Remove-List, 
	id-TNLA-Setup-List, 
	id-TNLA-Failed-To-Setup-List, 
	id-TraceActivation, 
	id-UEContextInfoHORequest, 
	id-UEContextInfoRetrUECtxtResp, 
	id-UEContextKeptIndicator, 
	id-UEContextRefAtSN-HORequest, 
	id-UEHistoryInformation, 
	id-UEIdentityIndexValue, 
	id-UERANPagingIdentity, 
	id-UESecurityCapabilities, 
	id-UserPlaneTrafficActivityReport, 
	id-XnRemovalThreshold, 
	id-PDUSessionAdmittedAddedAddReqAck, 
	id-PDUSessionNotAdmittedAddReqAck, 
	id-SN-to-MN-Container, 
	id-RRCConfigIndication, 
	id-SplitSRB-RRCTransfer, 
	id-UEReportRRCTransfer, 
	id-PDUSessionReleasedList-RelConf, 
	id-BearersSubjectToCounterCheck, 
	id-PDUSessionToBeReleasedList-RelRqd, 
	id-ResponseInfo-ReconfCompl, 
	id-initiatingNodeType-ResourceCoordRequest, 
	id-respondingNodeType-ResourceCoordResponse, 
	id-PDUSessionToBeReleased-RelReq, 
	id-PDUSession-SNChangeRequired-List, 
	id-PDUSession-SNChangeConfirm-List, 
	id-PDCPChangeIndication, 
	id-PC5QoSParameters, 
	id-SCGConfigurationQuery, 
	id-UEContextInfo-SNModRequest, 
	id-requestedSplitSRBrelease, 
	id-PDUSessionAdmitted-SNModResponse, 
	id-PDUSessionNotAdmitted-SNModResponse, 
	id-admittedSplitSRB, 
	id-admittedSplitSRBrelease, 
	id-PDUSessionAdmittedModSNModConfirm, 
	id-PDUSessionReleasedSNModConfirm, 
	id-s-ng-RANnode-SecurityKey, 
	id-PDUSessionToBeModifiedSNModRequired, 
	id-S-NG-RANnodeUE-AMBR, 
	id-PDUSessionToBeReleasedSNModRequired, 
	id-target-S-NG-RANnodeID, 
	id-S-NSSAI, 
	id-MR-DC-ResourceCoordinationInfo, 
	id-RANPagingFailure, 
	id-UERadioCapabilityForPaging, 
	id-PDUSessionDataForwarding-SNModResponse, 
	id-Secondary-MN-Xn-U-TNLInfoatM, 
	id-NE-DC-TDM-Pattern, 
	id-InterfaceInstanceIndication, 
	id-S-NG-RANnode-Addition-Trigger-Ind, 
	id-SNTriggered, 
	id-DRBs-transferred-to-MN, 
	id-TNLConfigurationInfo, 
	id-MessageOversizeNotification, 
	id-NG-RANTraceID, 
	id-FastMCGRecoveryRRCTransfer-SN-to-MN, 
	id-FastMCGRecoveryRRCTransfer-MN-to-SN, 
	id-RequestedFastMCGRecoveryViaSRB3, 
	id-AvailableFastMCGRecoveryViaSRB3, 
	id-RequestedFastMCGRecoveryViaSRB3Release, 
	id-ReleaseFastMCGRecoveryViaSRB3, 
	id-CHOinformation-Req, 
	id-CHOinformation-Ack, 
	id-targetCellsToCancel, 
	id-requestedTargetCellGlobalID, 
	id-DAPSResponseInfo-List, 
	id-CHO-MRDC-Indicator, 
	id-MobilityInformation, 
	id-InitiatingCondition-FailureIndication, 
	id-UEHistoryInformationFromTheUE, 
	id-HandoverReportType, 
	id-HandoverCause, 
	id-SourceCellCGI, 
	id-TargetCellCGI, 
	id-ReEstablishmentCellCGI, 
	id-TargetCellinEUTRAN, 
	id-SourceCellCRNTI, 
	id-UERLFReportContainer, 
	id-NGRAN-Node1-Measurement-ID, 
	id-NGRAN-Node2-Measurement-ID, 
	id-RegistrationRequest, 
	id-ReportCharacteristics, 
	id-CellToReport, 
	id-ReportingPeriodicity, 
	id-CellMeasurementResult, 
	id-NG-RANnode1CellID, 
	id-NG-RANnode2CellID, 
	id-NG-RANnode1MobilityParameters, 
	id-NG-RANnode2ProposedMobilityParameters, 
	id-MobilityParametersModificationRange, 
	id-RACHReportInformation, 
	id-IABNodeIndication, 
	id-UERadioCapabilityID, 



	maxnoofCellsinNG-RANnode, 
	maxnoofDRBs, 
	maxnoofPDUSessions, 
	maxnoofQoSFlows
FROM XnAP-Constants;






HandoverRequest ::= SEQUENCE {
	protocolIEs			ProtocolIE-Container	{{HandoverRequest-IEs}}, 
	...
}

HandoverRequest-IEs XNAP-PROTOCOL-IES ::= {
	{ ID id-sourceNG-RANnodeUEXnAPID			CRITICALITY reject	TYPE NG-RANnodeUEXnAPID							PRESENCE mandatory}|
	{ ID id-Cause								CRITICALITY reject	TYPE Cause										PRESENCE mandatory}|
	{ ID id-targetCellGlobalID					CRITICALITY reject	TYPE Target-CGI									PRESENCE mandatory}|
	{ ID id-GUAMI								CRITICALITY reject	TYPE GUAMI										PRESENCE mandatory}|
	{ ID id-UEContextInfoHORequest				CRITICALITY reject	TYPE UEContextInfoHORequest						PRESENCE mandatory}|
	{ ID id-TraceActivation						CRITICALITY ignore	TYPE TraceActivation							PRESENCE optional }|
	{ ID id-MaskedIMEISV						CRITICALITY ignore	TYPE MaskedIMEISV								PRESENCE optional }|
	{ ID id-UEHistoryInformation				CRITICALITY ignore	TYPE UEHistoryInformation						PRESENCE mandatory}|
	{ ID id-UEContextRefAtSN-HORequest			CRITICALITY ignore	TYPE UEContextRefAtSN-HORequest				PRESENCE optional }|
	{ ID id-CHOinformation-Req					CRITICALITY reject	TYPE CHOinformation-Req							PRESENCE optional }|
{ ID id-NRV2XServicesAuthorized				CRITICALITY ignore	TYPE NRV2XServicesAuthorized					PRESENCE optional }|
{ ID id-LTEV2XServicesAuthorized			CRITICALITY ignore	TYPE LTEV2XServicesAuthorized					PRESENCE optional }|
{ ID id-PC5QoSParameters					CRITICALITY ignore	TYPE PC5QoSParameters	
				PRESENCE optional }|
	{ ID id-MobilityInformation				CRITICALITY ignore	TYPE MobilityInformation								PRESENCE optional}|
	{ ID id-UEHistoryInformationFromTheUE	CRITICALITY ignore	TYPE UEHistoryInformationFromTheUE				PRESENCE optional }|
	{ ID id-IABNodeIndication					CRITICALITY reject	TYPE IABNodeIndication							PRESENCE optional}, 
	...
}

UEContextInfoHORequest ::= SEQUENCE {
	ng-c-UE-reference						AMF-UE-NGAP-ID, 
	cp-TNL-info-source						CPTransportLayerInformation, 
	ueSecurityCapabilities					UESecurityCapabilities, 
	securityInformation						AS-SecurityInformation, 
	indexToRatFrequencySelectionPriority	RFSP-Index															OPTIONAL, 
	ue-AMBR									UEAggregateMaximumBitRate, 
	pduSessionResourcesToBeSetup-List		PDUSessionResourcesToBeSetup-List, 
	rrc-Context								OCTET STRING, 
	locationReportingInformation			LocationReportingInformation										OPTIONAL, 
	mrl										MobilityRestrictionList												OPTIONAL, 
	iE-Extensions							ProtocolExtensionContainer { {UEContextInfoHORequest-ExtIEs} }	OPTIONAL, 
	...
}

UEContextInfoHORequest-ExtIEs XNAP-PROTOCOL-EXTENSION ::={
	{ ID id-FiveGCMobilityRestrictionListContainer 	CRITICALITY ignore	EXTENSION FiveGCMobilityRestrictionListContainer		PRESENCE optional }|
{ ID id-NRUESidelinkAggregateMaximumBitRate		CRITICALITY ignore	EXTENSION  NRUESidelinkAggregateMaximumBitRate	PRESENCE optional}|
{ ID id-LTEUESidelinkAggregateMaximumBitRate		CRITICALITY ignore EXTENSION	LTEUESidelinkAggregateMaximumBitRate	PRESENCE optional}|
	{ ID id-MDTPLMNList								CRITICALITY reject	EXTENSION MDTPLMNList											PRESENCE optional}|
	{ ID id-UERadioCapabilityID						CRITICALITY reject	EXTENSION UERadioCapabilityID								PRESENCE optional	}, 
	...
}

UEContextRefAtSN-HORequest ::= SEQUENCE {
	globalNG-RANNode-ID				GlobalNG-RANNode-ID, 
	sN-NG-RANnodeUEXnAPID			NG-RANnodeUEXnAPID, 
	iE-Extensions					ProtocolExtensionContainer { {UEContextRefAtSN-HORequest-ExtIEs} }	OPTIONAL, 
	...
}

UEContextRefAtSN-HORequest-ExtIEs XNAP-PROTOCOL-EXTENSION ::={
	...
}






HandoverRequestAcknowledge ::= SEQUENCE {
	protocolIEs			ProtocolIE-Container	{{HandoverRequestAcknowledge-IEs}}, 
	...
}

HandoverRequestAcknowledge-IEs XNAP-PROTOCOL-IES ::= {
	{ ID id-sourceNG-RANnodeUEXnAPID				CRITICALITY ignore	TYPE NG-RANnodeUEXnAPID								PRESENCE mandatory}|
	{ ID id-targetNG-RANnodeUEXnAPID				CRITICALITY ignore	TYPE NG-RANnodeUEXnAPID								PRESENCE mandatory}|
	{ ID id-PDUSessionResourcesAdmitted-List		CRITICALITY ignore	TYPE PDUSessionResourcesAdmitted-List			PRESENCE mandatory}|
	{ ID id-PDUSessionResourcesNotAdmitted-List		CRITICALITY ignore	TYPE PDUSessionResourcesNotAdmitted-List		PRESENCE optional }|
	{ ID id-Target2SourceNG-RANnodeTranspContainer	CRITICALITY ignore	TYPE OCTET STRING									PRESENCE mandatory}|
	{ ID id-UEContextKeptIndicator					CRITICALITY ignore	TYPE UEContextKeptIndicator						PRESENCE optional }|
	{ ID id-CriticalityDiagnostics					CRITICALITY ignore	TYPE CriticalityDiagnostics						PRESENCE optional }|
	{ ID id-DRBs-transferred-to-MN					CRITICALITY ignore	TYPE DRB-List										PRESENCE optional }|
	{ ID id-DAPSResponseInfo-List					CRITICALITY reject	TYPE DAPSResponseInfo-List						PRESENCE optional }|
	{ ID id-CHOinformation-Ack						CRITICALITY reject	TYPE CHOinformation-Ack								PRESENCE optional }, 
	...
}






HandoverPreparationFailure ::= SEQUENCE {
	protocolIEs			ProtocolIE-Container	{{HandoverPreparationFailure-IEs}}, 
	...
}

HandoverPreparationFailure-IEs XNAP-PROTOCOL-IES ::= {
	{ ID id-sourceNG-RANnodeUEXnAPID				CRITICALITY ignore	TYPE NG-RANnodeUEXnAPID							PRESENCE mandatory}|
	{ ID id-Cause									CRITICALITY ignore	TYPE Cause										PRESENCE mandatory}|
	{ ID id-CriticalityDiagnostics					CRITICALITY ignore	TYPE CriticalityDiagnostics					PRESENCE optional }|
	{ ID id-requestedTargetCellGlobalID				CRITICALITY reject	TYPE Target-CGI									PRESENCE optional}, 
	...
}






SNStatusTransfer ::= SEQUENCE {
	protocolIEs			ProtocolIE-Container	{{SNStatusTransfer-IEs}}, 
	...
}

SNStatusTransfer-IEs XNAP-PROTOCOL-IES ::= {
	{ ID id-sourceNG-RANnodeUEXnAPID				CRITICALITY reject		TYPE NG-RANnodeUEXnAPID							PRESENCE mandatory}|
	{ ID id-targetNG-RANnodeUEXnAPID				CRITICALITY reject		TYPE NG-RANnodeUEXnAPID							PRESENCE mandatory}|
	{ ID id-DRBsSubjectToStatusTransfer-List		CRITICALITY ignore		TYPE DRBsSubjectToStatusTransfer-List		PRESENCE mandatory}, 
	...
}






UEContextRelease ::= SEQUENCE {
	protocolIEs			ProtocolIE-Container	{{UEContextRelease-IEs}}, 
	...
}

UEContextRelease-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}, 
	...
}






HandoverCancel ::= SEQUENCE {
	protocolIEs			ProtocolIE-Container	{{HandoverCancel-IEs}}, 
	...
}

HandoverCancel-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY ignore		TYPE NG-RANnodeUEXnAPID							PRESENCE optional }|
	{ ID id-Cause										CRITICALITY ignore		TYPE Cause											PRESENCE mandatory}|
	{ ID id-targetCellsToCancel							CRITICALITY reject		TYPE TargetCellList								PRESENCE optional}, 
	...
}






HandoverSuccess ::= SEQUENCE {
	protocolIEs			ProtocolIE-Container	{{HandoverSuccess-IEs}}, 
	...
}

HandoverSuccess-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-requestedTargetCellGlobalID					CRITICALITY reject		TYPE Target-CGI										PRESENCE mandatory}, 
	...
}






ConditionalHandoverCancel ::= SEQUENCE {
	protocolIEs			ProtocolIE-Container	{{ ConditionalHandoverCancel-IEs}}, 
	...
}

ConditionalHandoverCancel-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-targetCellsToCancel							CRITICALITY reject		TYPE TargetCellList								PRESENCE optional}|
	{ ID id-Cause										CRITICALITY ignore		TYPE Cause											PRESENCE mandatory}, 
	...
}






EarlyStatusTransfer ::= SEQUENCE {
	protocolIEs			ProtocolIE-Container	{{ EarlyStatusTransfer-IEs}}, 
	...
}

EarlyStatusTransfer-IEs XNAP-PROTOCOL-IES ::= {
	{ ID id-sourceNG-RANnodeUEXnAPID					CRITICALITY reject		TYPE NG-RANnodeUEXnAPID							PRESENCE mandatory}|
	{ ID id-targetNG-RANnodeUEXnAPID					CRITICALITY reject		TYPE NG-RANnodeUEXnAPID							PRESENCE mandatory}|
	{ ID id-procedureStage								CRITICALITY reject		TYPE ProcedureStageChoice						PRESENCE mandatory}, 
	...
}

ProcedureStageChoice ::= CHOICE {
	first-dl-count						FirstDLCount, 
	dl-discarding						DLDiscarding, 
	choice-extension					ProtocolIE-Single-Container { {ProcedureStageChoice-ExtIEs} }
}

ProcedureStageChoice-ExtIEs XNAP-PROTOCOL-IES ::= {
	...
}

FirstDLCount ::= SEQUENCE {
	dRBsSubjectToEarlyStatusTransfer			DRBsSubjectToEarlyStatusTransfer-List, 
	iE-Extension								ProtocolExtensionContainer { {FirstDLCount-ExtIEs} }	OPTIONAL, 
	...
}

FirstDLCount-ExtIEs XNAP-PROTOCOL-EXTENSION ::= {
	...
}

DLDiscarding ::= SEQUENCE {
	dRBsSubjectToDLDiscarding					DRBsSubjectToDLDiscarding-List, 
	iE-Extension								ProtocolExtensionContainer { {DLDiscarding-ExtIEs} }	OPTIONAL, 
	...
}

DLDiscarding-ExtIEs XNAP-PROTOCOL-EXTENSION ::= {
	...
}






RANPaging ::= SEQUENCE {
	protocolIEs			ProtocolIE-Container	{{RANPaging-IEs}}, 
	...
}

RANPaging-IEs XNAP-PROTOCOL-IES ::= {
	{ ID id-UEIdentityIndexValue				CRITICALITY reject		TYPE UEIdentityIndexValue							PRESENCE mandatory}|
	{ ID id-UERANPagingIdentity					CRITICALITY ignore		TYPE UERANPagingIdentity							PRESENCE mandatory}|
	{ ID id-PagingDRX							CRITICALITY ignore		TYPE PagingDRX										PRESENCE mandatory}|
	{ ID id-RANPagingArea						CRITICALITY reject		TYPE RANPagingArea									PRESENCE mandatory}|
	{ ID id-PagingPriority						CRITICALITY ignore		TYPE PagingPriority									PRESENCE optional }|
	{ ID id-AssistanceDataForRANPaging			CRITICALITY ignore		TYPE AssistanceDataForRANPaging					PRESENCE optional }|
	{ ID id-UERadioCapabilityForPaging			CRITICALITY ignore		TYPE UERadioCapabilityForPaging					PRESENCE optional	}, 
	...
}






RetrieveUEContextRequest ::= SEQUENCE {
	protocolIEs			ProtocolIE-Container	{{RetrieveUEContextRequest-IEs}}, 
	...
}

RetrieveUEContextRequest-IEs XNAP-PROTOCOL-IES ::= {
	{ ID id-newNG-RANnodeUEXnAPID					CRITICALITY reject		TYPE NG-RANnodeUEXnAPID							PRESENCE mandatory}|
	{ ID id-UEContextID								CRITICALITY reject		TYPE UEContextID									PRESENCE mandatory}|
	{ ID id-MAC-I									CRITICALITY reject		TYPE MAC-I											PRESENCE mandatory}|
	{ ID id-new-NG-RAN-Cell-Identity				CRITICALITY reject		TYPE NG-RAN-Cell-Identity						PRESENCE mandatory}|
	{ ID id-RRCResumeCause							CRITICALITY ignore		TYPE RRCResumeCause									PRESENCE optional }, 
	...
}






RetrieveUEContextResponse ::= SEQUENCE {
	protocolIEs			ProtocolIE-Container	{{ RetrieveUEContextResponse-IEs}}, 
	...
}

RetrieveUEContextResponse-IEs XNAP-PROTOCOL-IES ::= {
	{ ID id-newNG-RANnodeUEXnAPID					CRITICALITY ignore		TYPE NG-RANnodeUEXnAPID							PRESENCE mandatory}|
	{ ID id-oldNG-RANnodeUEXnAPID					CRITICALITY ignore		TYPE NG-RANnodeUEXnAPID							PRESENCE mandatory}|
	{ ID id-GUAMI									CRITICALITY reject		TYPE GUAMI											PRESENCE mandatory}|
	{ ID id-UEContextInfoRetrUECtxtResp				CRITICALITY reject		TYPE UEContextInfoRetrUECtxtResp				PRESENCE mandatory}|
	{ ID id-TraceActivation							CRITICALITY ignore		TYPE TraceActivation								PRESENCE optional }|
	{ ID id-MaskedIMEISV							CRITICALITY ignore		TYPE MaskedIMEISV									PRESENCE optional }|
	{ ID id-LocationReportingInformation			CRITICALITY ignore		TYPE LocationReportingInformation				PRESENCE optional }|
	{ ID id-CriticalityDiagnostics					CRITICALITY ignore		TYPE CriticalityDiagnostics						PRESENCE optional }|
{ ID id-NRV2XServicesAuthorized			CRITICALITY ignore	TYPE NRV2XServicesAuthorized		PRESENCE optional}|
{ ID id-LTEV2XServicesAuthorized		CRITICALITY ignore	TYPE LTEV2XServicesAuthorized		PRESENCE optional}|
	{ ID id-PC5QoSParameters				CRITICALITY ignore	TYPE PC5QoSParameters			PRESENCE optional }|
	{ ID id-UEHistoryInformation				CRITICALITY ignore	TYPE UEHistoryInformation						PRESENCE optional}|
	{ ID id-UEHistoryInformationFromTheUE	CRITICALITY ignore	TYPE UEHistoryInformationFromTheUE				PRESENCE optional }|
	{ ID id-MDTPLMNList								CRITICALITY ignore		TYPE MDTPLMNList									PRESENCE optional }, 
	...
}






RetrieveUEContextFailure ::= SEQUENCE {
	protocolIEs			ProtocolIE-Container	{{ RetrieveUEContextFailure-IEs}}, 
	...
}

RetrieveUEContextFailure-IEs XNAP-PROTOCOL-IES ::= {	
	{ ID id-newNG-RANnodeUEXnAPID					CRITICALITY ignore		TYPE NG-RANnodeUEXnAPID							PRESENCE mandatory}|
	{ ID id-OldtoNewNG-RANnodeResumeContainer		CRITICALITY ignore		TYPE OCTET STRING									PRESENCE optional }|
	{ ID id-Cause									CRITICALITY ignore		TYPE Cause											PRESENCE mandatory}|
	{ ID id-CriticalityDiagnostics					CRITICALITY ignore		TYPE CriticalityDiagnostics						PRESENCE optional }, 
	...
}






XnUAddressIndication ::= SEQUENCE {
	protocolIEs			ProtocolIE-Container	{{ XnUAddressIndication-IEs}}, 
	...
}

XnUAddressIndication-IEs XNAP-PROTOCOL-IES ::= {
	{ ID id-newNG-RANnodeUEXnAPID					CRITICALITY ignore		TYPE NG-RANnodeUEXnAPID							PRESENCE mandatory}|
	{ ID id-oldNG-RANnodeUEXnAPID					CRITICALITY ignore		TYPE NG-RANnodeUEXnAPID							PRESENCE mandatory}|
	{ ID id-XnUAddressInfoperPDUSession-List		CRITICALITY reject		TYPE XnUAddressInfoperPDUSession-List		PRESENCE mandatory}|
	{ ID id-CHO-MRDC-Indicator						CRITICALITY reject		TYPE CHO-MRDC-Indicator							PRESENCE optional }, 
	...
}






SNodeAdditionRequest ::= SEQUENCE {
	protocolIEs			ProtocolIE-Container	{{ SNodeAdditionRequest-IEs}}, 
	...
}

SNodeAdditionRequest-IEs XNAP-PROTOCOL-IES ::= {
	{ ID id-M-NG-RANnodeUEXnAPID				CRITICALITY reject		TYPE NG-RANnodeUEXnAPID								PRESENCE mandatory}|
	{ ID id-UESecurityCapabilities				CRITICALITY reject		TYPE UESecurityCapabilities						PRESENCE mandatory}|
	{ ID id-s-ng-RANnode-SecurityKey			CRITICALITY reject		TYPE S-NG-RANnode-SecurityKey					PRESENCE mandatory}|
	{ ID id-S-NG-RANnodeUE-AMBR					CRITICALITY reject		TYPE UEAggregateMaximumBitRate					PRESENCE mandatory}|
	{ ID id-selectedPLMN						CRITICALITY ignore		TYPE PLMN-Identity									PRESENCE optional }|
	{ ID id-MobilityRestrictionList				CRITICALITY ignore		TYPE MobilityRestrictionList						PRESENCE optional }|
	{ ID id-indexToRatFrequSelectionPriority	CRITICALITY reject		TYPE RFSP-Index										PRESENCE optional }|
	{ ID id-PDUSessionToBeAddedAddReq			CRITICALITY reject		TYPE PDUSessionToBeAddedAddReq					PRESENCE mandatory}|
	{ ID id-MN-to-SN-Container					CRITICALITY reject		TYPE OCTET STRING									PRESENCE mandatory}|
	{ ID id-S-NG-RANnodeUEXnAPID				CRITICALITY reject		TYPE NG-RANnodeUEXnAPID								PRESENCE optional }|
	{ ID id-ExpectedUEBehaviour					CRITICALITY ignore		TYPE ExpectedUEBehaviour							PRESENCE optional }|
	{ ID id-requestedSplitSRB					CRITICALITY reject		TYPE SplitSRBsTypes									PRESENCE optional }|
	{ ID id-PCellID								CRITICALITY reject		TYPE GlobalNG-RANCell-ID							PRESENCE optional }|
	{ ID id-DesiredActNotificationLevel			CRITICALITY ignore		TYPE DesiredActNotificationLevel				PRESENCE optional }|
	{ ID id-AvailableDRBIDs						CRITICALITY reject		TYPE DRB-List										PRESENCE conditional}
 |
	{ ID id-S-NG-RANnodeMaxIPDataRate-UL		CRITICALITY reject		TYPE BitRate										PRESENCE optional }|
	{ ID id-S-NG-RANnodeMaxIPDataRate-DL		CRITICALITY reject		TYPE BitRate										PRESENCE optional }|
	{ ID id-LocationInformationSNReporting		CRITICALITY ignore		TYPE LocationInformationSNReporting			PRESENCE optional}|
	{ ID id-MR-DC-ResourceCoordinationInfo		CRITICALITY ignore		TYPE MR-DC-ResourceCoordinationInfo			PRESENCE optional }|
	{ ID id-MaskedIMEISV						CRITICALITY ignore		TYPE MaskedIMEISV									PRESENCE optional}|
	{ ID id-NE-DC-TDM-Pattern					CRITICALITY ignore		TYPE NE-DC-TDM-Pattern								PRESENCE optional}|
	{ ID id-S-NG-RANnode-Addition-Trigger-Ind	CRITICALITY reject		TYPE S-NG-RANnode-Addition-Trigger-Ind		PRESENCE optional}|
	{ ID id-TraceActivation						CRITICALITY ignore		TYPE TraceActivation								PRESENCE optional}|
	{ ID id-RequestedFastMCGRecoveryViaSRB3		CRITICALITY ignore		TYPE	 RequestedFastMCGRecoveryViaSRB3		PRESENCE optional}|
	{ ID id-UERadioCapabilityID					CRITICALITY reject		TYPE UERadioCapabilityID							PRESENCE optional}, 
	...
}

PDUSessionToBeAddedAddReq ::= SEQUENCE (SIZE(1..maxnoofPDUSessions)) OF PDUSessionToBeAddedAddReq-Item

PDUSessionToBeAddedAddReq-Item ::= SEQUENCE {
	pduSessionId			PDUSession-ID, 
	s-NSSAI					S-NSSAI, 
	sN-PDUSessionAMBR		PDUSessionAggregateMaximumBitRate			OPTIONAL, 
	sn-terminated			PDUSessionResourceSetupInfo-SNterminated	OPTIONAL, 
	mn-terminated			PDUSessionResourceSetupInfo-MNterminated	OPTIONAL, 



	iE-Extension			ProtocolExtensionContainer { {PDUSessionToBeAddedAddReq-Item-ExtIEs} }	OPTIONAL, 
	...
}

PDUSessionToBeAddedAddReq-Item-ExtIEs XNAP-PROTOCOL-EXTENSION ::= {
	...
}

RequestedFastMCGRecoveryViaSRB3 ::= ENUMERATED {true,  ...}






SNodeAdditionRequestAcknowledge ::= SEQUENCE {
	protocolIEs			ProtocolIE-Container	{{ SNodeAdditionRequestAcknowledge-IEs}}, 
	...
}

SNodeAdditionRequestAcknowledge-IEs XNAP-PROTOCOL-IES ::= {
	{ ID id-M-NG-RANnodeUEXnAPID				CRITICALITY reject		TYPE NG-RANnodeUEXnAPID							PRESENCE mandatory}|
	{ ID id-S-NG-RANnodeUEXnAPID				CRITICALITY reject		TYPE NG-RANnodeUEXnAPID							PRESENCE mandatory}|
	{ ID id-PDUSessionAdmittedAddedAddReqAck	CRITICALITY ignore		TYPE PDUSessionAdmittedAddedAddReqAck		PRESENCE mandatory}|
	{ ID id-PDUSessionNotAdmittedAddReqAck		CRITICALITY ignore		TYPE PDUSessionNotAdmittedAddReqAck		PRESENCE optional }|
	{ ID id-SN-to-MN-Container					CRITICALITY reject		TYPE OCTET STRING								PRESENCE mandatory}|
	{ ID id-admittedSplitSRB					CRITICALITY reject		TYPE SplitSRBsTypes								PRESENCE optional }|
	{ ID id-RRCConfigIndication					CRITICALITY reject		TYPE RRCConfigIndication						PRESENCE optional }|
	{ ID id-CriticalityDiagnostics				CRITICALITY ignore		TYPE CriticalityDiagnostics					PRESENCE optional }|
	{ ID id-LocationInformationSN				CRITICALITY ignore		TYPE Target-CGI									PRESENCE optional }|
	{ ID id-MR-DC-ResourceCoordinationInfo		CRITICALITY ignore		TYPE MR-DC-ResourceCoordinationInfo		PRESENCE optional }|
	{ ID id-AvailableFastMCGRecoveryViaSRB3		CRITICALITY ignore		TYPE AvailableFastMCGRecoveryViaSRB3		PRESENCE optional }, 
	...
}

PDUSessionAdmittedAddedAddReqAck ::= SEQUENCE (SIZE(1..maxnoofPDUSessions)) OF PDUSessionAdmittedAddedAddReqAck-Item

PDUSessionAdmittedAddedAddReqAck-Item ::= SEQUENCE {
	pduSessionId							PDUSession-ID, 
	sn-terminated			PDUSessionResourceSetupResponseInfo-SNterminated	OPTIONAL, 
	mn-terminated			PDUSessionResourceSetupResponseInfo-MNterminated	OPTIONAL, 



	iE-Extension			ProtocolExtensionContainer { {PDUSessionAdmittedAddedAddReqAck-Item-ExtIEs} }	OPTIONAL, 
	...
}

PDUSessionAdmittedAddedAddReqAck-Item-ExtIEs XNAP-PROTOCOL-EXTENSION ::= {
	...
}

PDUSessionNotAdmittedAddReqAck ::= SEQUENCE {
	pduSessionResourcesNotAdmitted-SNterminated		PDUSessionResourcesNotAdmitted-List OPTIONAL, 
	pduSessionResourcesNotAdmitted-MNterminated		PDUSessionResourcesNotAdmitted-List OPTIONAL, 
	iE-Extension			ProtocolExtensionContainer { {PDUSessionNotAdmittedAddReqAck-ExtIEs} }	OPTIONAL, 
	...
}

PDUSessionNotAdmittedAddReqAck-ExtIEs XNAP-PROTOCOL-EXTENSION ::= {
	...
}

AvailableFastMCGRecoveryViaSRB3 ::= ENUMERATED {true,  ...}






SNodeAdditionRequestReject ::= SEQUENCE {
	protocolIEs			ProtocolIE-Container	{{ SNodeAdditionRequestReject-IEs}}, 
	...
}

SNodeAdditionRequestReject-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional }, 
	...
}






SNodeReconfigurationComplete ::= SEQUENCE {
	protocolIEs			ProtocolIE-Container	{{ SNodeReconfigurationComplete-IEs}}, 
	...
}

SNodeReconfigurationComplete-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-ResponseInfo-ReconfCompl				CRITICALITY ignore		TYPE ResponseInfo-ReconfCompl					PRESENCE mandatory}, 
	...
}

ResponseInfo-ReconfCompl ::= SEQUENCE {
	responseType-ReconfComplete		ResponseType-ReconfComplete, 
	iE-Extensions						ProtocolExtensionContainer { {ResponseInfo-ReconfCompl-ExtIEs} } OPTIONAL, 
	...
}

ResponseInfo-ReconfCompl-ExtIEs XNAP-PROTOCOL-EXTENSION ::= {
	...
}

ResponseType-ReconfComplete ::= CHOICE {
	configuration-successfully-applied			Configuration-successfully-applied, 
	configuration-rejected-by-M-NG-RANNode		Configuration-rejected-by-M-NG-RANNode, 
	choice-extension					ProtocolIE-Single-Container { {ResponseType-ReconfComplete-ExtIEs} }
}

ResponseType-ReconfComplete-ExtIEs XNAP-PROTOCOL-IES ::= {
	...
}

Configuration-successfully-applied ::= SEQUENCE {
	m-NG-RANNode-to-S-NG-RANNode-Container		OCTET STRING		OPTIONAL, 
	iE-Extensions						ProtocolExtensionContainer { {Configuration-successfully-applied-ExtIEs} } OPTIONAL, 
	...
}

Configuration-successfully-applied-ExtIEs XNAP-PROTOCOL-EXTENSION ::= {
	...
}

Configuration-rejected-by-M-NG-RANNode ::= SEQUENCE {
	cause											Cause, 
	m-NG-RANNode-to-S-NG-RANNode-Container		OCTET STRING		OPTIONAL, 
	iE-Extensions						ProtocolExtensionContainer { {Configuration-rejected-by-M-NG-RANNode-ExtIEs} } OPTIONAL, 
	...
}

Configuration-rejected-by-M-NG-RANNode-ExtIEs XNAP-PROTOCOL-EXTENSION ::= {
	...
}






SNodeModificationRequest ::= SEQUENCE {
	protocolIEs			ProtocolIE-Container	{{ SNodeModificationRequest-IEs}}, 
	...
}

SNodeModificationRequest-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-PDCPChangeIndication					CRITICALITY ignore		TYPE PDCPChangeIndication						PRESENCE optional }|
	{ ID id-selectedPLMN							CRITICALITY ignore		TYPE PLMN-Identity									PRESENCE optional }|
	{ ID id-MobilityRestrictionList					CRITICALITY ignore		TYPE MobilityRestrictionList					PRESENCE optional }|
	{ ID id-SCGConfigurationQuery					CRITICALITY ignore		TYPE SCGConfigurationQuery						PRESENCE optional }|
	{ ID id-UEContextInfo-SNModRequest				CRITICALITY reject		TYPE UEContextInfo-SNModRequest				PRESENCE optional }|
	{ ID id-MN-to-SN-Container						CRITICALITY ignore		TYPE OCTET STRING									PRESENCE optional }|
	{ ID id-requestedSplitSRB						CRITICALITY ignore		TYPE SplitSRBsTypes									PRESENCE optional }|
	{ ID id-requestedSplitSRBrelease				CRITICALITY ignore		TYPE SplitSRBsTypes									PRESENCE optional }|
	{ ID id-DesiredActNotificationLevel				CRITICALITY ignore		TYPE DesiredActNotificationLevel				PRESENCE optional }|
	{ ID id-AdditionalDRBIDs						CRITICALITY reject		TYPE DRB-List										PRESENCE optional }|
	{ ID id-S-NG-RANnodeMaxIPDataRate-UL			CRITICALITY reject		TYPE BitRate										PRESENCE optional }|
	{ ID id-S-NG-RANnodeMaxIPDataRate-DL			CRITICALITY reject		TYPE BitRate										PRESENCE optional }|
	{ ID id-LocationInformationSNReporting			CRITICALITY ignore		TYPE LocationInformationSNReporting			PRESENCE optional}|
	{ ID id-MR-DC-ResourceCoordinationInfo			CRITICALITY ignore		TYPE MR-DC-ResourceCoordinationInfo			PRESENCE optional }|
	{ ID id-PCellID									CRITICALITY reject		TYPE GlobalNG-RANCell-ID							PRESENCE optional }|
	{ ID id-NE-DC-TDM-Pattern						CRITICALITY ignore		TYPE NE-DC-TDM-Pattern							PRESENCE optional}|
	{ ID id-RequestedFastMCGRecoveryViaSRB3			CRITICALITY ignore		TYPE RequestedFastMCGRecoveryViaSRB3			PRESENCE optional }|
	{ ID id-RequestedFastMCGRecoveryViaSRB3Release	CRITICALITY ignore		TYPE RequestedFastMCGRecoveryViaSRB3Release	PRESENCE optional }|
	{ ID id-SNTriggered						CRITICALITY ignore		TYPE SNTriggered							PRESENCE optional}, 
	...
}

UEContextInfo-SNModRequest ::= SEQUENCE {
	ueSecurityCapabilities							UESecurityCapabilities								OPTIONAL, 
	s-ng-RANnode-SecurityKey						S-NG-RANnode-SecurityKey							OPTIONAL, 
	s-ng-RANnodeUE-AMBR								UEAggregateMaximumBitRate							OPTIONAL, 
	indexToRatFrequencySelectionPriority			RFSP-Index											OPTIONAL, 
	lowerLayerPresenceStatusChange					LowerLayerPresenceStatusChange						OPTIONAL, 
	pduSessionResourceToBeAdded						PDUSessionsToBeAdded-SNModRequest-List				OPTIONAL, 
	pduSessionResourceToBeModified					PDUSessionsToBeModified-SNModRequest-List			OPTIONAL, 
	pduSessionResourceToBeReleased					PDUSessionsToBeReleased-SNModRequest-List			OPTIONAL, 
	iE-Extension			ProtocolExtensionContainer { {UEContextInfo-SNModRequest-ExtIEs} }			OPTIONAL, 
	...
}

UEContextInfo-SNModRequest-ExtIEs XNAP-PROTOCOL-EXTENSION ::= {
	...
}

PDUSessionsToBeAdded-SNModRequest-List ::= SEQUENCE (SIZE(1..maxnoofPDUSessions)) OF PDUSessionsToBeAdded-SNModRequest-Item

PDUSessionsToBeAdded-SNModRequest-Item ::= SEQUENCE {
	pduSessionId			PDUSession-ID, 
	s-NSSAI					S-NSSAI, 
	sN-PDUSessionAMBR		PDUSessionAggregateMaximumBitRate			OPTIONAL, 
	sn-terminated			PDUSessionResourceSetupInfo-SNterminated	OPTIONAL, 
	mn-terminated			PDUSessionResourceSetupInfo-MNterminated	OPTIONAL, 



	iE-Extension			ProtocolExtensionContainer { {PDUSessionsToBeAdded-SNModRequest-Item-ExtIEs} }	OPTIONAL, 
	...
}

PDUSessionsToBeAdded-SNModRequest-Item-ExtIEs XNAP-PROTOCOL-EXTENSION ::= {
	...
}

PDUSessionsToBeModified-SNModRequest-List ::= SEQUENCE (SIZE(1..maxnoofPDUSessions)) OF PDUSessionsToBeModified-SNModRequest-Item

PDUSessionsToBeModified-SNModRequest-Item ::= SEQUENCE {
	pduSessionId			PDUSession-ID, 
	sN-PDUSessionAMBR		PDUSessionAggregateMaximumBitRate				OPTIONAL, 
	sn-terminated			PDUSessionResourceModificationInfo-SNterminated	OPTIONAL, 
	mn-terminated			PDUSessionResourceModificationInfo-MNterminated	OPTIONAL, 



	iE-Extension			ProtocolExtensionContainer { {PDUSessionsToBeModified-SNModRequest-Item-ExtIEs} }	OPTIONAL, 
	...
}

PDUSessionsToBeModified-SNModRequest-Item-ExtIEs XNAP-PROTOCOL-EXTENSION ::= {
	{ID id-S-NSSAI		CRITICALITY reject	EXTENSION S-NSSAI		PRESENCE optional}, 
	...
}

PDUSessionsToBeReleased-SNModRequest-List ::= SEQUENCE {
	pdu-session-list		PDUSession-List-withCause				OPTIONAL, 
	iE-Extension			ProtocolExtensionContainer { {PDUSessionsToBeReleased-SNModRequest-List-ExtIEs} }	OPTIONAL, 
	...
}

PDUSessionsToBeReleased-SNModRequest-List-ExtIEs XNAP-PROTOCOL-EXTENSION ::= {
	...
}

RequestedFastMCGRecoveryViaSRB3Release ::= ENUMERATED {true,  ...}






SNodeModificationRequestAcknowledge ::= SEQUENCE {
	protocolIEs			ProtocolIE-Container	{{ SNodeModificationRequestAcknowledge-IEs}}, 
	...
}

SNodeModificationRequestAcknowledge-IEs XNAP-PROTOCOL-IES ::= {
	{ ID id-M-NG-RANnodeUEXnAPID					CRITICALITY ignore		TYPE NG-RANnodeUEXnAPID								PRESENCE mandatory}|
	{ ID id-S-NG-RANnodeUEXnAPID					CRITICALITY ignore		TYPE NG-RANnodeUEXnAPID								PRESENCE mandatory}|
	{ ID id-PDUSessionAdmitted-SNModResponse		CRITICALITY ignore		TYPE PDUSessionAdmitted-SNModResponse			PRESENCE optional }|
	{ ID id-PDUSessionNotAdmitted-SNModResponse		CRITICALITY ignore		TYPE PDUSessionNotAdmitted-SNModResponse		PRESENCE optional }|
	{ ID id-SN-to-MN-Container						CRITICALITY ignore		TYPE OCTET STRING										PRESENCE optional }|
	{ ID id-admittedSplitSRB						CRITICALITY ignore		TYPE SplitSRBsTypes										PRESENCE optional }|
	{ ID id-admittedSplitSRBrelease					CRITICALITY ignore		TYPE SplitSRBsTypes										PRESENCE optional }|
	{ ID id-CriticalityDiagnostics					CRITICALITY ignore		TYPE CriticalityDiagnostics							PRESENCE optional }|
	{ ID id-LocationInformationSN					CRITICALITY ignore		TYPE Target-CGI											PRESENCE optional }|
	{ ID id-MR-DC-ResourceCoordinationInfo			CRITICALITY ignore		TYPE MR-DC-ResourceCoordinationInfo				PRESENCE optional }|
	{ ID id-PDUSessionDataForwarding-SNModResponse	CRITICALITY ignore		TYPE PDUSessionDataForwarding-SNModResponse	PRESENCE optional }|
	{ ID id-RRCConfigIndication						CRITICALITY reject		TYPE RRCConfigIndication								PRESENCE optional }|
	{ ID id-AvailableFastMCGRecoveryViaSRB3			CRITICALITY ignore		TYPE AvailableFastMCGRecoveryViaSRB3				PRESENCE optional }|
	{ ID id-ReleaseFastMCGRecoveryViaSRB3	CRITICALITY ignore		TYPE ReleaseFastMCGRecoveryViaSRB3		PRESENCE optional }, 
	...
}
PDUSessionAdmitted-SNModResponse ::= SEQUENCE {
	pduSessionResourcesAdmittedToBeAdded			PDUSessionAdmittedToBeAddedSNModResponse 			OPTIONAL, 
	pduSessionResourcesAdmittedToBeModified			PDUSessionAdmittedToBeModifiedSNModResponse 		OPTIONAL, 
	pduSessionResourcesAdmittedToBeReleased			PDUSessionAdmittedToBeReleasedSNModResponse			OPTIONAL, 
	iE-Extension			ProtocolExtensionContainer { {PDUSessionAdmitted-SNModResponse-ExtIEs} }	OPTIONAL, 
	...
}

PDUSessionAdmitted-SNModResponse-ExtIEs XNAP-PROTOCOL-EXTENSION ::= {
	...
}

PDUSessionAdmittedToBeAddedSNModResponse ::= SEQUENCE (SIZE(1..maxnoofPDUSessions)) OF PDUSessionAdmittedToBeAddedSNModResponse-Item
PDUSessionAdmittedToBeAddedSNModResponse-Item ::= SEQUENCE {
	pduSessionId			PDUSession-ID, 
	sn-terminated			PDUSessionResourceSetupResponseInfo-SNterminated	OPTIONAL, 
	mn-terminated			PDUSessionResourceSetupResponseInfo-MNterminated	OPTIONAL, 



	iE-Extension			ProtocolExtensionContainer { {PDUSessionAdmittedToBeAddedSNModResponse-Item-ExtIEs} }	OPTIONAL, 
	...
}

PDUSessionAdmittedToBeAddedSNModResponse-Item-ExtIEs XNAP-PROTOCOL-EXTENSION ::= {
	...
}

PDUSessionAdmittedToBeModifiedSNModResponse::= SEQUENCE (SIZE(1..maxnoofPDUSessions)) OF PDUSessionAdmittedToBeModifiedSNModResponse-Item
PDUSessionAdmittedToBeModifiedSNModResponse-Item ::= SEQUENCE {
	pduSessionId			PDUSession-ID, 
	sn-terminated			PDUSessionResourceModificationResponseInfo-SNterminated	OPTIONAL, 
	mn-terminated			PDUSessionResourceModificationResponseInfo-MNterminated	OPTIONAL, 



	iE-Extension			ProtocolExtensionContainer { {PDUSessionAdmittedToBeModifiedSNModResponse-Item-ExtIEs} }	OPTIONAL, 
	...
}

PDUSessionAdmittedToBeModifiedSNModResponse-Item-ExtIEs XNAP-PROTOCOL-EXTENSION ::= {
	...
}

PDUSessionAdmittedToBeReleasedSNModResponse ::= SEQUENCE {
	sn-terminated			PDUSession-List-withDataForwardingRequest		OPTIONAL, 
	mn-terminated			PDUSession-List-withCause						OPTIONAL, 
	iE-Extension			ProtocolExtensionContainer { {PDUSessionAdmittedToBeReleasedSNModResponse-ExtIEs} }	OPTIONAL, 
	...
}

PDUSessionAdmittedToBeReleasedSNModResponse-ExtIEs XNAP-PROTOCOL-EXTENSION ::= {
	...
}

PDUSessionNotAdmitted-SNModResponse ::= SEQUENCE {
	pdu-Session-List		PDUSession-List OPTIONAL, 
	iE-Extension			ProtocolExtensionContainer { {PDUSessionNotAdmitted-SNModResponse-ExtIEs} }	OPTIONAL, 
	...
}

PDUSessionNotAdmitted-SNModResponse-ExtIEs XNAP-PROTOCOL-EXTENSION ::= {
	...
}


PDUSessionDataForwarding-SNModResponse ::= SEQUENCE {
	sn-terminated		PDUSession-List-withDataForwardingRequest, 
	iE-Extensions		ProtocolExtensionContainer { {PDUSessionDataForwarding-SNModResponse-ExtIEs} }	OPTIONAL, 
	...
}

PDUSessionDataForwarding-SNModResponse-ExtIEs XNAP-PROTOCOL-EXTENSION ::= {
	...
}

ReleaseFastMCGRecoveryViaSRB3 ::= ENUMERATED {true,  ...}






SNodeModificationRequestReject ::= SEQUENCE {
	protocolIEs			ProtocolIE-Container	{{ SNodeModificationRequestReject-IEs}}, 
	...
}

SNodeModificationRequestReject-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional }, 
	...
}






SNodeModificationRequired ::= SEQUENCE {
	protocolIEs			ProtocolIE-Container	{{ SNodeModificationRequired-IEs}}, 
	...
}

SNodeModificationRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-Cause									CRITICALITY ignore		TYPE Cause											PRESENCE mandatory}|
	{ ID id-PDCPChangeIndication					CRITICALITY ignore		TYPE PDCPChangeIndication						PRESENCE optional }|
	{ ID id-PDUSessionToBeModifiedSNModRequired		CRITICALITY ignore		TYPE PDUSessionToBeModifiedSNModRequired	PRESENCE optional }|
	{ ID id-PDUSessionToBeReleasedSNModRequired		CRITICALITY ignore		TYPE PDUSessionToBeReleasedSNModRequired	PRESENCE optional }|
	{ ID id-SN-to-MN-Container						CRITICALITY ignore		TYPE OCTET STRING									PRESENCE optional }|
	{ ID id-SpareDRBIDs								CRITICALITY ignore		TYPE DRB-List										PRESENCE optional }|
	{ ID id-RequiredNumberOfDRBIDs					CRITICALITY ignore		TYPE DRB-Number										PRESENCE optional }|
	{ ID id-LocationInformationSN					CRITICALITY ignore		TYPE Target-CGI										PRESENCE optional }|
	{ ID id-MR-DC-ResourceCoordinationInfo			CRITICALITY ignore		TYPE MR-DC-ResourceCoordinationInfo			PRESENCE optional }|
	{ ID id-RRCConfigIndication						CRITICALITY reject		TYPE RRCConfigIndication							PRESENCE optional }|
	{ ID id-AvailableFastMCGRecoveryViaSRB3			CRITICALITY ignore		TYPE AvailableFastMCGRecoveryViaSRB3			PRESENCE optional }|
	{ ID id-ReleaseFastMCGRecoveryViaSRB3			CRITICALITY ignore		TYPE ReleaseFastMCGRecoveryViaSRB3				PRESENCE optional }, 
	...
}
PDUSessionToBeModifiedSNModRequired::= SEQUENCE (SIZE (1.. maxnoofPDUSessions)) OF 	PDUSessionToBeModifiedSNModRequired-Item

PDUSessionToBeModifiedSNModRequired-Item ::= SEQUENCE {
	pduSessionId						PDUSession-ID, 
	sn-terminated			PDUSessionResourceModRqdInfo-SNterminated	OPTIONAL, 
	mn-terminated			PDUSessionResourceModRqdInfo-MNterminated	OPTIONAL, 



	iE-Extension		ProtocolExtensionContainer { {PDUSessionToBeModifiedSNModRequired-Item-ExtIEs} }	OPTIONAL, 
	...
}

PDUSessionToBeModifiedSNModRequired-Item-ExtIEs XNAP-PROTOCOL-EXTENSION ::= {
	...
}

PDUSessionToBeReleasedSNModRequired ::= SEQUENCE {
	sn-terminated			PDUSession-List-withDataForwardingRequest		OPTIONAL, 
	mn-terminated			PDUSession-List-withCause						OPTIONAL, 
	iE-Extension			ProtocolExtensionContainer { {PDUSessionToBeReleasedSNModRequired-ExtIEs} } OPTIONAL, 
	...
}

PDUSessionToBeReleasedSNModRequired-ExtIEs XNAP-PROTOCOL-EXTENSION ::= {
	...
}






SNodeModificationConfirm ::= SEQUENCE {
	protocolIEs			ProtocolIE-Container	{{ SNodeModificationConfirm-IEs}}, 
	...
}

SNodeModificationConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSessionAdmittedModSNModConfirm		CRITICALITY ignore		TYPE PDUSessionAdmittedModSNModConfirm		PRESENCE optional }|
	{ ID id-PDUSessionReleasedSNModConfirm			CRITICALITY ignore		TYPE PDUSessionReleasedSNModConfirm			PRESENCE optional }|
	{ ID id-MN-to-SN-Container						CRITICALITY ignore		TYPE OCTET STRING									PRESENCE optional }|
	{ ID id-AdditionalDRBIDs						CRITICALITY reject		TYPE DRB-List										PRESENCE optional }|
	{ ID id-CriticalityDiagnostics					CRITICALITY ignore		TYPE CriticalityDiagnostics						PRESENCE optional }|
	{ ID id-MR-DC-ResourceCoordinationInfo			CRITICALITY ignore		TYPE MR-DC-ResourceCoordinationInfo			PRESENCE optional }, 
	...
}

PDUSessionAdmittedModSNModConfirm ::= SEQUENCE (SIZE(1..maxnoofPDUSessions)) OF PDUSessionAdmittedModSNModConfirm-Item

PDUSessionAdmittedModSNModConfirm-Item ::= SEQUENCE {
	pduSessionId				PDUSession-ID, 
	sn-terminated			PDUSessionResourceModConfirmInfo-SNterminated	OPTIONAL, 
	mn-terminated			PDUSessionResourceModConfirmInfo-MNterminated	OPTIONAL, 



	iE-Extension			ProtocolExtensionContainer { {PDUSessionAdmittedModSNModConfirm-Item-ExtIEs} }	OPTIONAL, 
	...
}

PDUSessionAdmittedModSNModConfirm-Item-ExtIEs XNAP-PROTOCOL-EXTENSION ::= {
	...
}


PDUSessionReleasedSNModConfirm ::= SEQUENCE {
	sn-terminated			PDUSession-List-withDataForwardingFromTarget						OPTIONAL, 
	mn-terminated			PDUSession-List														OPTIONAL, 
	iE-Extension			ProtocolExtensionContainer { {PDUSessionAdmittedToBeReleasedSNModConfirm-ExtIEs} }	OPTIONAL, 
	...
}

PDUSessionAdmittedToBeReleasedSNModConfirm-ExtIEs XNAP-PROTOCOL-EXTENSION ::= {
	...
}






SNodeModificationRefuse ::= SEQUENCE {
	protocolIEs			ProtocolIE-Container	{{ SNodeModificationRefuse-IEs}}, 
	...
}

SNodeModificationRefuse-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-MN-to-SN-Container						CRITICALITY ignore		TYPE OCTET STRING									PRESENCE optional }|
	{ ID id-CriticalityDiagnostics					CRITICALITY ignore		TYPE CriticalityDiagnostics						PRESENCE optional }, 
	...
}






SNodeReleaseRequest ::= SEQUENCE {
	protocolIEs			ProtocolIE-Container	{{ SNodeReleaseRequest-IEs}}, 
	...
}

SNodeReleaseRequest-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE optional }|
	{ ID id-Cause									CRITICALITY ignore		TYPE Cause											PRESENCE mandatory}|
	{ ID id-PDUSessionToBeReleased-RelReq			CRITICALITY ignore		TYPE PDUSession-List-withCause					PRESENCE mandatory}|
	{ ID id-UEContextKeptIndicator					CRITICALITY ignore		TYPE UEContextKeptIndicator						PRESENCE optional }|
	{ ID id-MN-to-SN-Container						CRITICALITY ignore		TYPE OCTET STRING									PRESENCE optional }|
	{ ID id-DRBs-transferred-to-MN					CRITICALITY ignore		TYPE DRB-List										PRESENCE optional }, 
	...
}






SNodeReleaseRequestAcknowledge ::= SEQUENCE {
	protocolIEs			ProtocolIE-Container	{{ SNodeReleaseRequestAcknowledge-IEs}}, 
	...
}

SNodeReleaseRequestAcknowledge-IEs XNAP-PROTOCOL-IES ::= {
	{ ID id-M-NG-RANnodeUEXnAPID						CRITICALITY reject		TYPE NG-RANnodeUEXnAPID									PRESENCE mandatory}|
	{ ID id-S-NG-RANnodeUEXnAPID						CRITICALITY reject		TYPE NG-RANnodeUEXnAPID									PRESENCE optional }|
	{ ID id-PDUSessionToBeReleased-RelReqAck			CRITICALITY ignore		TYPE PDUSessionToBeReleasedList-RelReqAck			PRESENCE optional	}|
	{ ID id-CriticalityDiagnostics						CRITICALITY ignore		TYPE CriticalityDiagnostics							PRESENCE optional }, 
	...
}

PDUSessionToBeReleasedList-RelReqAck ::= SEQUENCE {
	pduSessionsToBeReleasedList-SNterminated		PDUSession-List-withDataForwardingRequest												OPTIONAL, 
	iE-Extensions									ProtocolExtensionContainer { {PDUSessionToBeReleasedList-RelReqAck-ExtIEs} }	OPTIONAL, 
	...
}

PDUSessionToBeReleasedList-RelReqAck-ExtIEs XNAP-PROTOCOL-EXTENSION ::= {
	...
}






SNodeReleaseReject ::= SEQUENCE {
	protocolIEs			ProtocolIE-Container	{{ SNodeReleaseReject-IEs}}, 
	...
}

SNodeReleaseReject-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE optional }|
	{ ID id-Cause									CRITICALITY ignore		TYPE Cause											PRESENCE mandatory}|
	{ ID id-CriticalityDiagnostics					CRITICALITY ignore		TYPE CriticalityDiagnostics						PRESENCE optional }, 
	...
}






SNodeReleaseRequired ::= SEQUENCE {
	protocolIEs			ProtocolIE-Container	{{ SNodeReleaseRequired-IEs}}, 
	...
}

SNodeReleaseRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-PDUSessionToBeReleasedList-RelRqd		CRITICALITY ignore		TYPE PDUSessionToBeReleasedList-RelRqd		PRESENCE optional }|
	{ ID id-Cause									CRITICALITY ignore		TYPE Cause											PRESENCE mandatory}|
	{ ID id-SN-to-MN-Container						CRITICALITY ignore		TYPE OCTET STRING									PRESENCE optional }, 
	...
}

PDUSessionToBeReleasedList-RelRqd ::= SEQUENCE {
	pduSessionsToBeReleasedList-SNterminated		PDUSession-List-withDataForwardingRequest						OPTIONAL, 
	iE-Extensions					ProtocolExtensionContainer { {PDUSessionToBeReleasedList-RelRqd-ExtIEs} }	OPTIONAL, 
	...
}

PDUSessionToBeReleasedList-RelRqd-ExtIEs XNAP-PROTOCOL-EXTENSION ::= {
	...
}






SNodeReleaseConfirm ::= SEQUENCE {
	protocolIEs			ProtocolIE-Container	{{ SNodeReleaseConfirm-IEs}}, 
	...
}

SNodeReleaseConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSessionReleasedList-RelConf			CRITICALITY ignore		TYPE PDUSessionReleasedList-RelConf			PRESENCE optional }|
	{ ID id-CriticalityDiagnostics					CRITICALITY ignore		TYPE CriticalityDiagnostics						PRESENCE optional }, 
	...
}

PDUSessionReleasedList-RelConf ::= SEQUENCE {
	pduSessionsReleasedList-SNterminated		PDUSession-List-withDataForwardingFromTarget					OPTIONAL, 
	iE-Extensions					ProtocolExtensionContainer { {PDUSessionReleasedList-RelConf-ExtIEs} }	OPTIONAL, 
	...
}

PDUSessionReleasedList-RelConf-ExtIEs XNAP-PROTOCOL-EXTENSION ::= {
	...
}






SNodeCounterCheckRequest ::= SEQUENCE {
	protocolIEs			ProtocolIE-Container	{{ SNodeCounterCheckRequest-IEs}}, 
	...
}

SNodeCounterCheckRequest-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-BearersSubjectToCounterCheck			CRITICALITY ignore		TYPE BearersSubjectToCounterCheck-List		PRESENCE mandatory}, 
	...
}

BearersSubjectToCounterCheck-List ::= SEQUENCE (SIZE(1..maxnoofDRBs)) OF BearersSubjectToCounterCheck-Item

BearersSubjectToCounterCheck-Item ::= SEQUENCE {
	drb-ID							DRB-ID, 
	ul-count						INTEGER (0.. 4294967295), 
	dl-count						INTEGER (0.. 4294967295), 
	iE-Extensions					ProtocolExtensionContainer { {BearersSubjectToCounterCheck-Item-ExtIEs} }	OPTIONAL, 
	...
}

BearersSubjectToCounterCheck-Item-ExtIEs XNAP-PROTOCOL-EXTENSION ::= {
	...
}






SNodeChangeRequired ::= SEQUENCE {
	protocolIEs			ProtocolIE-Container	{{ SNodeChangeRequired-IEs}}, 
	...
}

SNodeChangeRequired-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-target-S-NG-RANnodeID					CRITICALITY reject		TYPE GlobalNG-RANNode-ID							PRESENCE mandatory}|
	{ ID id-Cause									CRITICALITY ignore		TYPE Cause											PRESENCE mandatory}|
	{ ID id-PDUSession-SNChangeRequired-List		CRITICALITY ignore		TYPE PDUSession-SNChangeRequired-List		PRESENCE optional }|
	{ ID id-SN-to-MN-Container						CRITICALITY reject		TYPE OCTET STRING									PRESENCE mandatory}, 
	...
}

PDUSession-SNChangeRequired-List ::= SEQUENCE (SIZE(1..maxnoofPDUSessions)) OF PDUSession-SNChangeRequired-Item

PDUSession-SNChangeRequired-Item ::= SEQUENCE {
	pduSessionId				PDUSession-ID, 
	sn-terminated			PDUSessionResourceChangeRequiredInfo-SNterminated	OPTIONAL, 
	mn-terminated			PDUSessionResourceChangeRequiredInfo-MNterminated	OPTIONAL, 


	iE-Extension			ProtocolExtensionContainer { {PDUSession-SNChangeRequired-Item-ExtIEs} }	OPTIONAL, 
	...
}

PDUSession-SNChangeRequired-Item-ExtIEs XNAP-PROTOCOL-EXTENSION ::= {
	...
}






SNodeChangeConfirm ::= SEQUENCE {
	protocolIEs			ProtocolIE-Container	{{ SNodeChangeConfirm-IEs}}, 
	...
}

SNodeChangeConfirm-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-PDUSession-SNChangeConfirm-List			CRITICALITY ignore		TYPE PDUSession-SNChangeConfirm-List			PRESENCE optional }|
	{ ID id-CriticalityDiagnostics					CRITICALITY ignore		TYPE CriticalityDiagnostics						PRESENCE optional }, 
	...
}
PDUSession-SNChangeConfirm-List ::= SEQUENCE (SIZE(1..maxnoofPDUSessions)) OF PDUSession-SNChangeConfirm-Item

PDUSession-SNChangeConfirm-Item ::= SEQUENCE {
	pduSessionId				PDUSession-ID, 
	sn-terminated			PDUSessionResourceChangeConfirmInfo-SNterminated	OPTIONAL, 
	mn-terminated			PDUSessionResourceChangeConfirmInfo-MNterminated	OPTIONAL, 


	iE-Extension			ProtocolExtensionContainer { {PDUSession-SNChangeConfirm-Item-ExtIEs} }	OPTIONAL, 
	...
}

PDUSession-SNChangeConfirm-Item-ExtIEs XNAP-PROTOCOL-EXTENSION ::= {
	...
}






SNodeChangeRefuse ::= SEQUENCE {
	protocolIEs			ProtocolIE-Container	{{ SNodeChangeRefuse-IEs}}, 
	...
}

SNodeChangeRefuse-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-Cause									CRITICALITY ignore		TYPE Cause											PRESENCE mandatory}|
	{ ID id-CriticalityDiagnostics					CRITICALITY ignore		TYPE CriticalityDiagnostics						PRESENCE optional }, 
	...
}






RRCTransfer ::= SEQUENCE {
	protocolIEs			ProtocolIE-Container	{{ RRCTransfer-IEs}}, 
	...
}

RRCTransfer-IEs XNAP-PROTOCOL-IES ::= {
	{ ID id-M-NG-RANnodeUEXnAPID					CRITICALITY reject		TYPE NG-RANnodeUEXnAPID							PRESENCE mandatory}|
	{ ID id-S-NG-RANnodeUEXnAPID					CRITICALITY reject		TYPE NG-RANnodeUEXnAPID							PRESENCE mandatory}|
	{ ID id-SplitSRB-RRCTransfer					CRITICALITY reject		TYPE SplitSRB-RRCTransfer						PRESENCE optional }|
	{ ID id-UEReportRRCTransfer						CRITICALITY reject		TYPE UEReportRRCTransfer							PRESENCE optional }|
	{ ID id-FastMCGRecoveryRRCTransfer-SN-to-MN		CRITICALITY ignore		TYPE FastMCGRecoveryRRCTransfer				PRESENCE optional}|
	{ ID id-FastMCGRecoveryRRCTransfer-MN-to-SN		CRITICALITY ignore		TYPE FastMCGRecoveryRRCTransfer				PRESENCE optional}, 
	...
}

SplitSRB-RRCTransfer ::= SEQUENCE {
	rrcContainer					OCTET STRING						OPTIONAL, 
	srbType							ENUMERATED {srb1,  srb2,  ...}, 
	deliveryStatus					DeliveryStatus						OPTIONAL, 
	iE-Extensions					ProtocolExtensionContainer { {SplitSRB-RRCTransfer-ExtIEs} } OPTIONAL, 
	...
}

SplitSRB-RRCTransfer-ExtIEs XNAP-PROTOCOL-EXTENSION ::= {
	...
}

UEReportRRCTransfer::= SEQUENCE {
	rrcContainer					OCTET STRING, 
	iE-Extensions					ProtocolExtensionContainer { {UEReportRRCTransfer-ExtIEs} } OPTIONAL, 
	...
}

UEReportRRCTransfer-ExtIEs XNAP-PROTOCOL-EXTENSION ::= {
	...
}

FastMCGRecoveryRRCTransfer::= SEQUENCE {
	rrcContainer					OCTET STRING, 
	iE-Extensions					ProtocolExtensionContainer { { FastMCGRecoveryRRCTransfer-ExtIEs} } OPTIONAL, 
	...
}

FastMCGRecoveryRRCTransfer-ExtIEs XNAP-PROTOCOL-EXTENSION ::= {
	...
}






NotificationControlIndication ::= SEQUENCE {
	protocolIEs			ProtocolIE-Container	{{NotificationControlIndication-IEs}}, 
	...
}

NotificationControlIndication-IEs XNAP-PROTOCOL-IES ::= {
	{ ID id-M-NG-RANnodeUEXnAPID				CRITICALITY reject		TYPE NG-RANnodeUEXnAPID							PRESENCE mandatory}|
	{ ID id-S-NG-RANnodeUEXnAPID				CRITICALITY reject		TYPE NG-RANnodeUEXnAPID							PRESENCE mandatory}|
	{ ID id-PDUSessionResourcesNotifyList		CRITICALITY reject		TYPE PDUSessionResourcesNotifyList			PRESENCE optional }, 
	...
}

PDUSessionResourcesNotifyList ::= SEQUENCE (SIZE(1..maxnoofPDUSessions)) OF PDUSessionResourcesNotify-Item

PDUSessionResourcesNotify-Item ::= SEQUENCE {
	pduSessionId						PDUSession-ID, 
	qosFlowsNotificationContrIndInfo	QoSFlowNotificationControlIndicationInfo, 
	iE-Extensions						ProtocolExtensionContainer { {PDUSessionResourcesNotify-Item-ExtIEs} } OPTIONAL, 
	...
}

PDUSessionResourcesNotify-Item-ExtIEs XNAP-PROTOCOL-EXTENSION ::= {
	...
}






ActivityNotification ::= SEQUENCE {
	protocolIEs			ProtocolIE-Container	{{ActivityNotification-IEs}}, 
	...
}

ActivityNotification-IEs XNAP-PROTOCOL-IES ::= {
	{ ID id-M-NG-RANnodeUEXnAPID					CRITICALITY ignore		TYPE NG-RANnodeUEXnAPID							PRESENCE mandatory}|
	{ ID id-S-NG-RANnodeUEXnAPID					CRITICALITY ignore		TYPE NG-RANnodeUEXnAPID							PRESENCE mandatory}|
	{ ID id-UserPlaneTrafficActivityReport			CRITICALITY ignore		TYPE UserPlaneTrafficActivityReport			PRESENCE optional }|
	{ ID id-PDUSessionResourcesActivityNotifyList	CRITICALITY ignore		TYPE PDUSessionResourcesActivityNotifyList	PRESENCE optional }|
	{ ID id-RANPagingFailure						CRITICALITY ignore		TYPE RANPagingFailure								PRESENCE optional }, 
	...
}

PDUSessionResourcesActivityNotifyList ::= SEQUENCE (SIZE(1..maxnoofPDUSessions)) OF PDUSessionResourcesActivityNotify-Item

PDUSessionResourcesActivityNotify-Item ::= SEQUENCE {
	pduSessionId						PDUSession-ID, 
	pduSessionLevelUPactivityreport		UserPlaneTrafficActivityReport											OPTIONAL, 
	qosFlowsActivityNotifyList			QoSFlowsActivityNotifyList												OPTIONAL, 
	iE-Extensions						ProtocolExtensionContainer { {PDUSessionResourcesActivityNotify-Item-ExtIEs} } OPTIONAL, 
	...
}

PDUSessionResourcesActivityNotify-Item-ExtIEs XNAP-PROTOCOL-EXTENSION ::= {
	...
}

QoSFlowsActivityNotifyList ::= SEQUENCE (SIZE(1..maxnoofQoSFlows)) OF QoSFlowsActivityNotifyItem

QoSFlowsActivityNotifyItem ::= SEQUENCE {
	qosFlowIdentifier					QoSFlowIdentifier, 
	pduSessionLevelUPactivityreport		UserPlaneTrafficActivityReport, 
	iE-Extensions						ProtocolExtensionContainer { {QoSFlowsActivityNotifyItem-ExtIEs} } OPTIONAL, 
	...
}

QoSFlowsActivityNotifyItem-ExtIEs XNAP-PROTOCOL-EXTENSION ::= {
	...
}






XnSetupRequest ::= SEQUENCE {
	protocolIEs			ProtocolIE-Container	{{ XnSetupRequest-IEs}}, 
	...
}

XnSetupRequest-IEs XNAP-PROTOCOL-IES ::= {
	{ ID id-GlobalNG-RAN-node-ID					CRITICALITY reject	TYPE GlobalNG-RANNode-ID			PRESENCE mandatory}|
	{ ID id-TAISupport-list						CRITICALITY reject	TYPE TAISupport-List							PRESENCE mandatory}|
	{ ID id-AMF-Region-Information				CRITICALITY reject	TYPE AMF-Region-Information						PRESENCE mandatory}|
	{ ID id-List-of-served-cells-NR				CRITICALITY reject	TYPE ServedCells-NR								PRESENCE optional }|
	{ ID id-List-of-served-cells-E-UTRA			CRITICALITY reject	TYPE ServedCells-E-UTRA							PRESENCE optional }|
	{ ID id-InterfaceInstanceIndication			CRITICALITY reject	TYPE InterfaceInstanceIndication				PRESENCE optional }|
	{ ID id-TNLConfigurationInfo				CRITICALITY ignore	TYPE TNLConfigurationInfo						PRESENCE optional}|
	{ ID id-PartialListIndicator-NR				CRITICALITY ignore	TYPE PartialListIndicator						PRESENCE optional }|
	{ ID id-CellAndCapacityAssistanceInfo-NR 	CRITICALITY ignore 	TYPE CellAndCapacityAssistanceInfo-NR		PRESENCE optional }|
	{ ID id-PartialListIndicator-EUTRA			CRITICALITY ignore	TYPE PartialListIndicator						PRESENCE optional }|
	{ ID id-CellAndCapacityAssistanceInfo-EUTRA	CRITICALITY ignore 	TYPE CellAndCapacityAssistanceInfo-EUTRA	PRESENCE optional }, 
	...
}






XnSetupResponse ::= SEQUENCE {
	protocolIEs			ProtocolIE-Container	{{ XnSetupResponse-IEs}}, 
	...
}

XnSetupResponse-IEs XNAP-PROTOCOL-IES ::= {
	{ ID id-GlobalNG-RAN-node-ID				CRITICALITY reject	TYPE GlobalNG-RANNode-ID						PRESENCE mandatory}|
	{ ID id-TAISupport-list						CRITICALITY reject	TYPE TAISupport-List							PRESENCE mandatory}|
	{ ID id-List-of-served-cells-NR				CRITICALITY reject	TYPE ServedCells-NR								PRESENCE optional }|
	{ ID id-List-of-served-cells-E-UTRA			CRITICALITY reject	TYPE ServedCells-E-UTRA							PRESENCE optional }|
	{ ID id-CriticalityDiagnostics				CRITICALITY ignore	TYPE CriticalityDiagnostics						PRESENCE optional }|
	{ ID id-AMF-Region-Information				CRITICALITY reject	TYPE AMF-Region-Information						PRESENCE optional }|
	{ ID id-InterfaceInstanceIndication			CRITICALITY reject	TYPE InterfaceInstanceIndication				PRESENCE optional }|
	{ ID id-TNLConfigurationInfo				CRITICALITY ignore	TYPE TNLConfigurationInfo						PRESENCE optional	}|
	{ ID id-PartialListIndicator-NR				CRITICALITY ignore	TYPE PartialListIndicator						PRESENCE optional }|
	{ ID id-CellAndCapacityAssistanceInfo-NR 	CRITICALITY ignore 	TYPE CellAndCapacityAssistanceInfo-NR		PRESENCE optional }|
	{ ID id-PartialListIndicator-EUTRA			CRITICALITY ignore	TYPE PartialListIndicator						PRESENCE optional }|
	{ ID id-CellAndCapacityAssistanceInfo-EUTRA	CRITICALITY ignore 	TYPE CellAndCapacityAssistanceInfo-EUTRA	PRESENCE optional }, 
	...
}






XnSetupFailure ::= SEQUENCE {
	protocolIEs			ProtocolIE-Container	{{ XnSetupFailure-IEs}}, 
	...
}

XnSetupFailure-IEs XNAP-PROTOCOL-IES ::= {
	{ ID id-Cause						CRITICALITY ignore	TYPE Cause							PRESENCE mandatory}|
	{ ID id-TimeToWait					CRITICALITY ignore	TYPE TimeToWait						PRESENCE optional }|
	{ ID id-CriticalityDiagnostics		CRITICALITY ignore	TYPE CriticalityDiagnostics			PRESENCE optional }|
	{ ID id-InterfaceInstanceIndication	CRITICALITY reject	TYPE InterfaceInstanceIndication	PRESENCE optional }|
	{ ID id-MessageOversizeNotification	CRITICALITY ignore	TYPE MessageOversizeNotification	PRESENCE optional }, 
	...
}






NGRANNodeConfigurationUpdate ::= SEQUENCE {
	protocolIEs			ProtocolIE-Container	{{ NGRANNodeConfigurationUpdate-IEs}}, 
	...
}

NGRANNodeConfigurationUpdate-IEs XNAP-PROTOCOL-IES ::= {
	{ ID id-TAISupport-list							CRITICALITY reject	TYPE TAISupport-List									PRESENCE optional }|
	{ ID id-ConfigurationUpdateInitiatingNodeChoice	CRITICALITY ignore	TYPE ConfigurationUpdateInitiatingNodeChoice	PRESENCE mandatory}|
	{ ID id-TNLA-To-Add-List						CRITICALITY ignore	TYPE TNLA-To-Add-List									PRESENCE optional }|
	{ ID id-TNLA-To-Remove-List						CRITICALITY ignore	TYPE TNLA-To-Remove-List								PRESENCE optional }|
	{ ID id-TNLA-To-Update-List						CRITICALITY ignore	TYPE TNLA-To-Update-List								PRESENCE optional }|
	{ ID id-GlobalNG-RAN-node-ID					CRITICALITY reject	TYPE GlobalNG-RANNode-ID								PRESENCE optional }|
	{ ID id-AMF-Region-Information-To-Add			CRITICALITY reject	TYPE AMF-Region-Information							PRESENCE optional }|
	{ ID id-AMF-Region-Information-To-Delete		CRITICALITY reject	TYPE AMF-Region-Information							PRESENCE optional }|
	{ ID id-InterfaceInstanceIndication				CRITICALITY reject	TYPE InterfaceInstanceIndication					PRESENCE optional }|
	{ ID id-TNLConfigurationInfo					CRITICALITY ignore	TYPE TNLConfigurationInfo			   				PRESENCE optional	}, 
	...
}

ConfigurationUpdateInitiatingNodeChoice ::= CHOICE {
	gNB									ProtocolIE-Container	{ {ConfigurationUpdate-gNB} }, 
	ng-eNB								ProtocolIE-Container	{ {ConfigurationUpdate-ng-eNB} }, 
	choice-extension					ProtocolIE-Single-Container { {ServedCellsToUpdateInitiatingNodeChoice-ExtIEs} }
}

ServedCellsToUpdateInitiatingNodeChoice-ExtIEs XNAP-PROTOCOL-IES ::= {
	...
}

ConfigurationUpdate-gNB XNAP-PROTOCOL-IES ::= {
	{ ID id-servedCellsToUpdate-NR			CRITICALITY ignore TYPE	ServedCellsToUpdate-NR					PRESENCE optional }|
	{ ID id-cellAssistanceInfo-NR			CRITICALITY ignore TYPE	CellAssistanceInfo-NR					PRESENCE optional }|
	{ ID id-cellAssistanceInfo-EUTRA			CRITICALITY ignore TYPE	CellAssistanceInfo-EUTRA					PRESENCE optional }, 
	...
}


ConfigurationUpdate-ng-eNB XNAP-PROTOCOL-IES ::= {
	{ ID id-servedCellsToUpdate-E-UTRA	CRITICALITY ignore TYPE	ServedCellsToUpdate-E-UTRA				PRESENCE optional }|
	{ ID id-cellAssistanceInfo-NR		CRITICALITY ignore TYPE	CellAssistanceInfo-NR			PRESENCE optional }|
	{ ID id-cellAssistanceInfo-EUTRA			CRITICALITY ignore TYPE	CellAssistanceInfo-EUTRA					PRESENCE optional }, 
		...
}






NGRANNodeConfigurationUpdateAcknowledge ::= SEQUENCE {
	protocolIEs			ProtocolIE-Container	{{ NGRANNodeConfigurationUpdateAcknowledge-IEs}}, 
	...
}

NGRANNodeConfigurationUpdateAcknowledge-IEs XNAP-PROTOCOL-IES ::= {
	{ ID id-RespondingNodeTypeConfigUpdateAck	CRITICALITY ignore	TYPE RespondingNodeTypeConfigUpdateAck		PRESENCE mandatory}|
	{ ID id-TNLA-Setup-List						CRITICALITY ignore	TYPE TNLA-Setup-List							PRESENCE optional }|
	{ ID id-TNLA-Failed-To-Setup-List			CRITICALITY ignore	TYPE TNLA-Failed-To-Setup-List				PRESENCE optional }|
	{ ID id-CriticalityDiagnostics				CRITICALITY ignore	TYPE CriticalityDiagnostics						PRESENCE optional }|
	{ ID id-InterfaceInstanceIndication			CRITICALITY reject	TYPE InterfaceInstanceIndication				PRESENCE optional }|
	{ ID id-TNLConfigurationInfo				CRITICALITY ignore	TYPE TNLConfigurationInfo						PRESENCE optional	}, 
	...
}
RespondingNodeTypeConfigUpdateAck ::= CHOICE {
	ng-eNB					RespondingNodeTypeConfigUpdateAck-ng-eNB, 
	gNB						RespondingNodeTypeConfigUpdateAck-gNB, 
	choice-extension		ProtocolIE-Single-Container { {RespondingNodeTypeConfigUpdateAck-ExtIEs} }
}

RespondingNodeTypeConfigUpdateAck-ExtIEs XNAP-PROTOCOL-IES ::= {
	...
}

RespondingNodeTypeConfigUpdateAck-ng-eNB ::= SEQUENCE {
	iE-Extension		ProtocolExtensionContainer { {RespondingNodeTypeConfigUpdateAck-ng-eNB-ExtIEs} }	OPTIONAL, 
	...
}

RespondingNodeTypeConfigUpdateAck-ng-eNB-ExtIEs XNAP-PROTOCOL-EXTENSION ::= {
	...
}


RespondingNodeTypeConfigUpdateAck-gNB ::= SEQUENCE {
	served-NR-Cells		ServedCells-NR																OPTIONAL, 
	iE-Extension		ProtocolExtensionContainer { {RespondingNodeTypeConfigUpdateAck-gNB-ExtIEs} }	OPTIONAL, 
	...
}

RespondingNodeTypeConfigUpdateAck-gNB-ExtIEs XNAP-PROTOCOL-EXTENSION ::= {
	{ ID id-PartialListIndicator-NR				CRITICALITY ignore	EXTENSION PartialListIndicator						PRESENCE optional }|
	{ ID id-CellAndCapacityAssistanceInfo-NR 	CRITICALITY ignore 	EXTENSION CellAndCapacityAssistanceInfo-NR		PRESENCE optional }, 
	...
}






NGRANNodeConfigurationUpdateFailure ::= SEQUENCE {
	protocolIEs			ProtocolIE-Container	{{NGRANNodeConfigurationUpdateFailure-IEs}}, 
	...
}

NGRANNodeConfigurationUpdateFailure-IEs XNAP-PROTOCOL-IES ::= {
	{ ID id-Cause						CRITICALITY ignore	TYPE Cause							PRESENCE mandatory}|
	{ ID id-TimeToWait					CRITICALITY ignore	TYPE TimeToWait						PRESENCE optional }|
	{ ID id-CriticalityDiagnostics		CRITICALITY ignore	TYPE CriticalityDiagnostics			PRESENCE optional }|
	{ ID id-InterfaceInstanceIndication	CRITICALITY reject	TYPE InterfaceInstanceIndication	PRESENCE optional }, 
	...
}






E-UTRA-NR-CellResourceCoordinationRequest ::= SEQUENCE {
	protocolIEs			ProtocolIE-Container	{{E-UTRA-NR-CellResourceCoordinationRequest-IEs}}, 
	...
}

E-UTRA-NR-CellResourceCoordinationRequest-IEs XNAP-PROTOCOL-IES ::= {
	{ ID id-initiatingNodeType-ResourceCoordRequest	CRITICALITY reject	TYPE InitiatingNodeType-ResourceCoordRequest		PRESENCE mandatory}|
	{ ID id-InterfaceInstanceIndication				CRITICALITY reject	TYPE InterfaceInstanceIndication						PRESENCE optional }, 
	...
}

InitiatingNodeType-ResourceCoordRequest ::= CHOICE {
	ng-eNB								ResourceCoordRequest-ng-eNB-initiated, 
	gNB									ResourceCoordRequest-gNB-initiated, 
	choice-extension					ProtocolIE-Single-Container { {InitiatingNodeType-ResourceCoordRequest-ExtIEs} }
}

InitiatingNodeType-ResourceCoordRequest-ExtIEs XNAP-PROTOCOL-IES ::= {
	...
}

ResourceCoordRequest-ng-eNB-initiated ::= SEQUENCE {
	dataTrafficResourceIndication		DataTrafficResourceIndication, 
	spectrumSharingGroupID				SpectrumSharingGroupID, 
	listofE-UTRACells					SEQUENCE (SIZE(1.. maxnoofCellsinNG-RANnode)) OF E-UTRA-CGI							OPTIONAL, 
	iE-Extensions						ProtocolExtensionContainer { {ResourceCoordRequest-ng-eNB-initiated-ExtIEs} }	OPTIONAL, 
	...
}

ResourceCoordRequest-ng-eNB-initiated-ExtIEs XNAP-PROTOCOL-EXTENSION ::= {
	...
}


ResourceCoordRequest-gNB-initiated ::= SEQUENCE {
	dataTrafficResourceIndication		DataTrafficResourceIndication, 
	listofE-UTRACells					SEQUENCE (SIZE(1.. maxnoofCellsinNG-RANnode)) OF E-UTRA-CGI						OPTIONAL, 
	spectrumSharingGroupID				SpectrumSharingGroupID, 
	listofNRCells						SEQUENCE (SIZE(1.. maxnoofCellsinNG-RANnode)) OF NR-CGI								OPTIONAL, 
	iE-Extensions						ProtocolExtensionContainer { {ResourceCoordRequest-gNB-initiated-ExtIEs} }	OPTIONAL, 
	...
}

ResourceCoordRequest-gNB-initiated-ExtIEs XNAP-PROTOCOL-EXTENSION ::= {
	...
}






E-UTRA-NR-CellResourceCoordinationResponse::= SEQUENCE {
	protocolIEs			ProtocolIE-Container	{{E-UTRA-NR-CellResourceCoordinationResponse-IEs}}, 
	...
}

E-UTRA-NR-CellResourceCoordinationResponse-IEs XNAP-PROTOCOL-IES ::= {
	{ ID id-respondingNodeType-ResourceCoordResponse  CRITICALITY reject  	TYPE RespondingNodeType-ResourceCoordResponse 	PRESENCE mandatory}|
	{ ID id-InterfaceInstanceIndication				CRITICALITY reject	TYPE InterfaceInstanceIndication						PRESENCE optional }, 
	...
}

RespondingNodeType-ResourceCoordResponse ::= CHOICE {
	ng-eNB								ResourceCoordResponse-ng-eNB-initiated, 
	gNB									ResourceCoordResponse-gNB-initiated, 
	choice-extension					ProtocolIE-Single-Container { {RespondingNodeType-ResourceCoordResponse-ExtIEs} }
}

RespondingNodeType-ResourceCoordResponse-ExtIEs XNAP-PROTOCOL-IES ::= {
	...
}

ResourceCoordResponse-ng-eNB-initiated ::= SEQUENCE {
	dataTrafficResourceIndication		DataTrafficResourceIndication, 
	spectrumSharingGroupID				SpectrumSharingGroupID, 
	listofE-UTRACells					SEQUENCE (SIZE(1.. maxnoofCellsinNG-RANnode)) OF E-UTRA-CGI								OPTIONAL, 
	iE-Extensions						ProtocolExtensionContainer { {ResourceCoordResponse-ng-eNB-initiated-ExtIEs} }		OPTIONAL, 
	...
}

ResourceCoordResponse-ng-eNB-initiated-ExtIEs XNAP-PROTOCOL-EXTENSION ::= {
	...
}


ResourceCoordResponse-gNB-initiated ::= SEQUENCE {
	dataTrafficResourceIndication		DataTrafficResourceIndication, 
	spectrumSharingGroupID				SpectrumSharingGroupID, 
	listofNRCells						SEQUENCE (SIZE(1.. maxnoofCellsinNG-RANnode)) OF NR-CGI									OPTIONAL, 
	iE-Extensions						ProtocolExtensionContainer { {ResourceCoordResponse-gNB-initiated-ExtIEs} }		OPTIONAL, 
	...
}

ResourceCoordResponse-gNB-initiated-ExtIEs XNAP-PROTOCOL-EXTENSION ::= {
	...
}






SecondaryRATDataUsageReport ::= SEQUENCE {
	protocolIEs		ProtocolIE-Container		{{SecondaryRATDataUsageReport-IEs}}, 
	...
}

SecondaryRATDataUsageReport-IEs XNAP-PROTOCOL-IES ::= {
	{ ID id-M-NG-RANnodeUEXnAPID					CRITICALITY reject		TYPE NG-RANnodeUEXnAPID								PRESENCE mandatory}|
	{ ID id-S-NG-RANnodeUEXnAPID					CRITICALITY reject		TYPE NG-RANnodeUEXnAPID								PRESENCE mandatory}|
	{ ID id-PDUSessionResourceSecondaryRATUsageList	CRITICALITY reject		TYPE PDUSessionResourceSecondaryRATUsageList	PRESENCE mandatory}, 
	...
}






XnRemovalRequest ::= SEQUENCE {
	protocolIEs			ProtocolIE-Container	{{ XnRemovalRequest-IEs}}, 
	...
}

XnRemovalRequest-IEs XNAP-PROTOCOL-IES ::= {
	{ ID id-GlobalNG-RAN-node-ID		CRITICALITY reject	TYPE GlobalNG-RANNode-ID			PRESENCE mandatory}|
	{ ID id-XnRemovalThreshold			CRITICALITY reject	TYPE XnBenefitValue					PRESENCE optional }|
	{ ID id-InterfaceInstanceIndication	CRITICALITY reject	TYPE InterfaceInstanceIndication	PRESENCE optional }, 
	...
}






XnRemovalResponse ::= SEQUENCE {
	protocolIEs			ProtocolIE-Container	{{ XnRemovalResponse-IEs}}, 
	...
}

XnRemovalResponse-IEs XNAP-PROTOCOL-IES ::= {
	{ ID id-GlobalNG-RAN-node-ID		CRITICALITY reject	TYPE GlobalNG-RANNode-ID			PRESENCE mandatory}|
	{ ID id-CriticalityDiagnostics		CRITICALITY ignore	TYPE CriticalityDiagnostics			PRESENCE optional }|
	{ ID id-InterfaceInstanceIndication	CRITICALITY reject	TYPE InterfaceInstanceIndication	PRESENCE optional }, 
	...
}






XnRemovalFailure ::= SEQUENCE {
	protocolIEs			ProtocolIE-Container	{{ XnRemovalFailure-IEs}}, 
	...
}

XnRemovalFailure-IEs XNAP-PROTOCOL-IES ::= {
	{ ID id-Cause						CRITICALITY ignore	TYPE Cause							PRESENCE mandatory}|
	{ ID id-CriticalityDiagnostics		CRITICALITY ignore	TYPE CriticalityDiagnostics			PRESENCE optional }|
	{ ID id-InterfaceInstanceIndication	CRITICALITY reject	TYPE InterfaceInstanceIndication	PRESENCE optional }, 
	...
}






CellActivationRequest ::= SEQUENCE {
	protocolIEs			ProtocolIE-Container	{{ CellActivationRequest-IEs}}, 
	...
}

CellActivationRequest-IEs XNAP-PROTOCOL-IES ::= {
	{ ID id-ServedCellsToActivate					CRITICALITY reject		TYPE ServedCellsToActivate						PRESENCE mandatory}|
	{ ID id-ActivationIDforCellActivation			CRITICALITY reject		TYPE ActivationIDforCellActivation			PRESENCE mandatory}|
	{ ID id-InterfaceInstanceIndication				CRITICALITY reject		TYPE InterfaceInstanceIndication				PRESENCE optional }, 
	...
}

ServedCellsToActivate ::= CHOICE {
	nr-cells							SEQUENCE (SIZE(1..maxnoofCellsinNG-RANnode)) OF NR-CGI, 
	e-utra-cells						SEQUENCE (SIZE(1..maxnoofCellsinNG-RANnode)) OF E-UTRA-CGI, 
	choice-extension					ProtocolIE-Single-Container { {ServedCellsToActivate-ExtIEs} }
}

ServedCellsToActivate-ExtIEs XNAP-PROTOCOL-IES ::= {
	...
}






CellActivationResponse ::= SEQUENCE {
	protocolIEs			ProtocolIE-Container	{{CellActivationResponse-IEs}}, 
	...
}

CellActivationResponse-IEs XNAP-PROTOCOL-IES ::= {
	{ ID id-ActivatedServedCells					CRITICALITY reject		TYPE ActivatedServedCells						PRESENCE mandatory}|
	{ ID id-ActivationIDforCellActivation			CRITICALITY reject		TYPE ActivationIDforCellActivation			PRESENCE mandatory}|
	{ ID id-CriticalityDiagnostics					CRITICALITY ignore		TYPE CriticalityDiagnostics						PRESENCE optional }|
	{ ID id-InterfaceInstanceIndication			CRITICALITY reject		TYPE InterfaceInstanceIndication				PRESENCE optional }, 
	...
}

ActivatedServedCells ::= CHOICE {
	nr-cells							SEQUENCE (SIZE(1..maxnoofCellsinNG-RANnode)) OF NR-CGI, 
	e-utra-cells						SEQUENCE (SIZE(1..maxnoofCellsinNG-RANnode)) OF E-UTRA-CGI, 
	choice-extension					ProtocolIE-Single-Container { {ActivatedServedCells-ExtIEs} }
}

ActivatedServedCells-ExtIEs XNAP-PROTOCOL-IES ::= {
	...
}






CellActivationFailure ::= SEQUENCE {
	protocolIEs			ProtocolIE-Container	{{CellActivationFailure-IEs}}, 
	...
}

CellActivationFailure-IEs XNAP-PROTOCOL-IES ::= {
	{ ID id-ActivationIDforCellActivation			CRITICALITY reject		TYPE ActivationIDforCellActivation			PRESENCE mandatory}|
	{ ID id-Cause									CRITICALITY ignore		TYPE Cause											PRESENCE mandatory}|
	{ ID id-CriticalityDiagnostics					CRITICALITY ignore		TYPE CriticalityDiagnostics						PRESENCE optional }|
	{ ID id-InterfaceInstanceIndication				CRITICALITY reject		TYPE InterfaceInstanceIndication				PRESENCE optional }, 
	...
}






ResetRequest ::= SEQUENCE {
	protocolIEs			ProtocolIE-Container	{{ResetRequest-IEs}}, 
	...
}

ResetRequest-IEs XNAP-PROTOCOL-IES ::= {
	{ ID id-ResetRequestTypeInfo					CRITICALITY reject		TYPE ResetRequestTypeInfo						PRESENCE mandatory}|
	{ ID id-Cause									CRITICALITY ignore		TYPE Cause											PRESENCE mandatory}|
	{ ID id-InterfaceInstanceIndication				CRITICALITY reject		TYPE InterfaceInstanceIndication				PRESENCE optional }, 
	...
}






ResetResponse ::= SEQUENCE {
	protocolIEs			ProtocolIE-Container	{{ResetResponse-IEs}}, 
	...
}

ResetResponse-IEs XNAP-PROTOCOL-IES ::= {
	{ ID id-ResetResponseTypeInfo					CRITICALITY reject		TYPE ResetResponseTypeInfo						PRESENCE mandatory}|
	{ ID id-CriticalityDiagnostics					CRITICALITY ignore		TYPE CriticalityDiagnostics						PRESENCE optional }|
	{ ID id-InterfaceInstanceIndication				CRITICALITY reject		TYPE InterfaceInstanceIndication				PRESENCE optional }, 
	...
}






ErrorIndication ::= SEQUENCE {
	protocolIEs			ProtocolIE-Container	{{ErrorIndication-IEs}}, 
	...
}

ErrorIndication-IEs XNAP-PROTOCOL-IES ::= {
	{ ID id-oldNG-RANnodeUEXnAPID					CRITICALITY ignore		TYPE NG-RANnodeUEXnAPID							PRESENCE optional }|
	{ ID id-newNG-RANnodeUEXnAPID					CRITICALITY ignore		TYPE NG-RANnodeUEXnAPID							PRESENCE optional }|
	{ ID id-Cause									CRITICALITY ignore		TYPE Cause											PRESENCE optional }|
	{ ID id-CriticalityDiagnostics					CRITICALITY ignore		TYPE CriticalityDiagnostics						PRESENCE optional }|
	{ ID id-InterfaceInstanceIndication				CRITICALITY reject		TYPE InterfaceInstanceIndication				PRESENCE optional }, 
	...
}






PrivateMessage ::= SEQUENCE {
	privateIEs		PrivateIE-Container	{{PrivateMessage-IEs}}, 
	...
}

PrivateMessage-IEs XNAP-PRIVATE-IES ::= {
	...
}






TraceStart ::= SEQUENCE {
	protocolIEs		ProtocolIE-Container		{ {TraceStartIEs} }, 
	...
}

TraceStartIEs XNAP-PROTOCOL-IES ::= {
	{ ID id-M-NG-RANnodeUEXnAPID					CRITICALITY reject	TYPE NG-RANnodeUEXnAPID							PRESENCE mandatory}|
	{ ID id-S-NG-RANnodeUEXnAPID					CRITICALITY reject	TYPE NG-RANnodeUEXnAPID							PRESENCE mandatory}|
	{ ID id-TraceActivation							CRITICALITY ignore	TYPE TraceActivation							PRESENCE optional }, 
	...
}






DeactivateTrace ::= SEQUENCE {
	protocolIEs		ProtocolIE-Container		{ {DeactivateTraceIEs} }, 
	...
}

DeactivateTraceIEs XNAP-PROTOCOL-IES ::= {
	{ ID id-M-NG-RANnodeUEXnAPID					CRITICALITY reject	TYPE NG-RANnodeUEXnAPID							PRESENCE mandatory}|
	{ ID id-S-NG-RANnodeUEXnAPID					CRITICALITY reject	TYPE NG-RANnodeUEXnAPID							PRESENCE mandatory}|
	{ ID id-NG-RANTraceID							CRITICALITY ignore	TYPE NG-RANTraceID								PRESENCE mandatory}, 
	...
}






FailureIndication ::= SEQUENCE {
	protocolIEs			ProtocolIE-Container	{{FailureIndication-IEs}}, 
	...
}

FailureIndication-IEs XNAP-PROTOCOL-IES ::= {
	{ ID id-InitiatingCondition-FailureIndication				CRITICALITY reject		TYPE InitiatingCondition-FailureIndication							PRESENCE mandatory}, 
	...
}






HandoverReport ::= SEQUENCE {
	protocolIEs			ProtocolIE-Container	{{ HandoverReport-IEs}}, 
	...
}

HandoverReport-IEs XNAP-PROTOCOL-IES ::= {
	{ ID id-HandoverReportType					CRITICALITY ignore		TYPE HandoverReportType	PRESENCE mandatory}|
	{ ID id-HandoverCause					CRITICALITY ignore		TYPE Cause				PRESENCE mandatory}|
	{ ID id-SourceCellCGI				CRITICALITY ignore		TYPE GlobalNG-RANCell-ID			PRESENCE mandatory }| 
	{ ID id-TargetCellCGI            	CRITICALITY ignore		TYPE GlobalNG-RANCell-ID			PRESENCE mandatory }|
	{ ID id-ReEstablishmentCellCGI   	CRITICALITY ignore		TYPE GlobalNG-RANCell-ID			PRESENCE conditional }|

	{ ID id-TargetCellinEUTRAN   		CRITICALITY ignore		TYPE TargetCellinEUTRAN	PRESENCE conditional }|

	{ ID id-SourceCellCRNTI   			CRITICALITY ignore		TYPE C-RNTI           	PRESENCE optional }|
	{ ID id-MobilityInformation   		CRITICALITY ignore		TYPE MobilityInformation	PRESENCE optional }|
	{ ID id-UERLFReportContainer   		CRITICALITY ignore		TYPE UERLFReportContainer	PRESENCE optional }, 
	...
}






ResourceStatusRequest ::= SEQUENCE {
	protocolIEs		ProtocolIE-Container	{{ResourceStatusRequest-IEs}}, 
	...
}

ResourceStatusRequest-IEs XNAP-PROTOCOL-IES ::= {
	{ ID id-NGRAN-Node1-Measurement-ID			CRITICALITY reject	TYPE Measurement-ID					PRESENCE mandatory}|
	{ ID id-NGRAN-Node2-Measurement-ID		CRITICALITY ignore	TYPE Measurement-ID					PRESENCE conditional}|

	{ ID id-RegistrationRequest					CRITICALITY reject	TYPE RegistrationRequest				PRESENCE mandatory}|
	{ ID id-ReportCharacteristics			CRITICALITY reject	TYPE ReportCharacteristics			PRESENCE conditional}|

	{ ID id-CellToReport							CRITICALITY ignore	TYPE CellToReport					PRESENCE optional}|
	{ ID id-ReportingPeriodicity				CRITICALITY ignore	TYPE ReportingPeriodicity			PRESENCE optional}, 
	...
}






ResourceStatusResponse ::= SEQUENCE {
	protocolIEs		ProtocolIE-Container	{{ResourceStatusResponse-IEs}}, 
	...
}

ResourceStatusResponse-IEs XNAP-PROTOCOL-IES ::= {
	{ ID id-NGRAN-Node1-Measurement-ID			CRITICALITY reject	TYPE Measurement-ID							PRESENCE mandatory}|
	{ ID id-NGRAN-Node2-Measurement-ID			CRITICALITY reject	TYPE Measurement-ID							PRESENCE mandatory}|
	{ ID id-CriticalityDiagnostics				CRITICALITY ignore	TYPE CriticalityDiagnostics					PRESENCE optional}, 
	...
}






ResourceStatusFailure ::= SEQUENCE {
	protocolIEs		ProtocolIE-Container	{{ResourceStatusFailure-IEs}}, 
	...
}

ResourceStatusFailure-IEs XNAP-PROTOCOL-IES ::= {
	{ ID id-NGRAN-Node1-Measurement-ID				CRITICALITY reject	TYPE Measurement-ID									PRESENCE mandatory}|
	{ ID id-NGRAN-Node2-Measurement-ID				CRITICALITY reject	TYPE Measurement-ID									PRESENCE mandatory}|
	{ ID id-Cause									CRITICALITY ignore	TYPE Cause											PRESENCE mandatory}|
	{ ID id-CriticalityDiagnostics					CRITICALITY ignore	TYPE CriticalityDiagnostics						PRESENCE optional}, 
	...
}






ResourceStatusUpdate ::= SEQUENCE {
	protocolIEs		ProtocolIE-Container	{{ResourceStatusUpdate-IEs}}, 
	...
}

ResourceStatusUpdate-IEs XNAP-PROTOCOL-IES ::= {
	{ ID id-NGRAN-Node1-Measurement-ID		CRITICALITY reject	TYPE Measurement-ID					PRESENCE mandatory}|
	{ ID id-NGRAN-Node2-Measurement-ID		CRITICALITY reject	TYPE Measurement-ID					PRESENCE mandatory}|
{ ID id-CellMeasurementResult		CRITICALITY ignore	TYPE CellMeasurementResult		PRESENCE mandatory}, 
	...
}






MobilityChangeRequest ::= SEQUENCE {
	protocolIEs		ProtocolIE-Container	{{MobilityChangeRequest-IEs}}, 
	...
}

MobilityChangeRequest-IEs XNAP-PROTOCOL-IES ::= {
	{ ID id-NG-RANnode1CellID			CRITICALITY reject	TYPE GlobalNG-RANCell-ID							PRESENCE mandatory}|
	{ ID id-NG-RANnode2CellID			CRITICALITY reject	TYPE GlobalNG-RANCell-ID							PRESENCE mandatory}|
	{ ID id-NG-RANnode1MobilityParameters	CRITICALITY reject		TYPE MobilityParametersInformation	PRESENCE optional}|
	{ ID id-NG-RANnode2ProposedMobilityParameters	CRITICALITY reject	TYPE MobilityParametersInformation	PRESENCE optional}|
	{ ID id-Cause						CRITICALITY ignore	TYPE Cause					PRESENCE mandatory}, 
	...
}






MobilityChangeAcknowledge ::= SEQUENCE {
	protocolIEs		ProtocolIE-Container	{{MobilityChangeAcknowledge-IEs}}, 
	...
}

MobilityChangeAcknowledge-IEs XNAP-PROTOCOL-IES ::= {
	{ ID id-NG-RANnode1CellID			CRITICALITY reject	TYPE GlobalNG-RANCell-ID							PRESENCE mandatory}|
	{ ID id-NG-RANnode2CellID			CRITICALITY reject	TYPE GlobalNG-RANCell-ID							PRESENCE mandatory}|
	{ ID id-CriticalityDiagnostics				CRITICALITY ignore	TYPE CriticalityDiagnostics					PRESENCE optional}, 
	...
}






MobilityChangeFailure ::= SEQUENCE {
	protocolIEs		ProtocolIE-Container	{{MobilityChangeFailure-IEs}}, 
	...
}

MobilityChangeFailure-IEs XNAP-PROTOCOL-IES ::= {
	{ ID id-NG-RANnode1CellID			CRITICALITY reject	TYPE GlobalNG-RANCell-ID							PRESENCE mandatory}|
	{ ID id-NG-RANnode2CellID			CRITICALITY reject	TYPE GlobalNG-RANCell-ID							PRESENCE mandatory}|
	{ ID id-Cause									CRITICALITY ignore	TYPE Cause											PRESENCE mandatory}|
	{ ID id-MobilityParametersModificationRange 	CRITICALITY reject		TYPE MobilityParametersModificationRange	PRESENCE optional}|
	{ ID id-CriticalityDiagnostics					CRITICALITY ignore	TYPE CriticalityDiagnostics						PRESENCE optional}, 
	...
}






AccessAndMobilityIndication ::= SEQUENCE {
	protocolIEs			ProtocolIE-Container	{{ AccessAndMobilityIndication-IEs}}, 
	...
}
AccessAndMobilityIndication-IEs XNAP-PROTOCOL-IES ::= {
	{ ID id-RACHReportInformation			CRITICALITY ignore		TYPE RACHReportInformation			PRESENCE optional}, 
	...
}


END






XnAP-IEs {
itu-t (0) identified-organization (4) etsi (0) mobileDomain (0)
ngran-access (22) modules (3) xnap (2) version1 (1) xnap-IEs (2) }

DEFINITIONS AUTOMATIC TAGS ::=

BEGIN

IMPORTS


	id-CNTypeRestrictionsForEquivalent, 
	id-CNTypeRestrictionsForServing, 
	id-Additional-UL-NG-U-TNLatUPF-List, 
	id-AlternativeQoSParaSetList, 
	id-CurrentQoSParaSetIndex, 
	id-DefaultDRB-Allowed, 
	id-DLCarrierList, 
	id-EndpointIPAddressAndPort, 
	id-ExtendedTAISliceSupportList, 
	id-FiveGCMobilityRestrictionListContainer, 
	id-SecondarydataForwardingInfoFromTarget-List, 
	id-LastE-UTRANPLMNIdentity, 
	id-IntendedTDD-DL-ULConfiguration-NR, 
	id-MaxIPrate-DL, 
	id-SecurityResult, 
	id-OldQoSFlowMap-ULendmarkerexpected, 
	id-PDUSessionCommonNetworkInstance, 
	id-BPLMN-ID-Info-EUTRA, 
	id-BPLMN-ID-Info-NR, 
	id-DRBsNotAdmittedSetupModifyList, 
	id-Secondary-MN-Xn-U-TNLInfoatM, 
	id-ULForwardingProposal, 
	id-DRB-IDs-takenintouse, 
	id-SplitSessionIndicator, 
	id-NonGBRResources-Offered, 
	id-MDT-Configuration, 
	id-TraceCollectionEntityURI, 
	id-NPN-Broadcast-Information, 
	id-NPNPagingAssistanceInformation, 
	id-NPNMobilityInformation, 
	id-NPN-Support, 
	id-LTEUESidelinkAggregateMaximumBitRate, 
	id-NRUESidelinkAggregateMaximumBitRate, 
	id-ExtendedRATRestrictionInformation,  
	id-QoSMonitoringRequest, 
	id-DAPSRequestInfo,  
	id-OffsetOfNbiotChannelNumberToDL-EARFCN, 
	id-OffsetOfNbiotChannelNumberToUL-EARFCN, 
	id-NBIoT-UL-DL-AlignmentOffset, 
	id-TDDULDLConfigurationCommonNR, 
	id-CarrierList, 
	id-ULCarrierList, 
	id-FrequencyShift7p5khz, 
	id-SSB-PositionsInBurst, 
	id-NRCellPRACHConfig, 
	id-Redundant-UL-NG-U-TNLatUPF, 
	id-Redundant-DL-NG-U-TNLatNG-RAN, 
	id-CNPacketDelayBudgetDownlink, 
	id-CNPacketDelayBudgetUplink, 
	id-ExtendedPacketDelayBudget, 
	id-Additional-Redundant-UL-NG-U-TNLatUPF-List, 
	id-RedundantCommonNetworkInstance, 
	id-TSCTrafficCharacteristics, 
	id-RedundantQoSFlowIndicator, 
	id-Additional-PDCP-Duplication-TNL-List, 
	id-RedundantPDUSessionInformation, 
	id-UsedRSNInformation, 
	id-RLCDuplicationInformation, 
	id-CSI-RSTransmissionIndication, 
	id-UERadioCapabilityID, 
	maxEARFCN, 
	maxnoofAllowedAreas, 
	maxnoofAMFRegions, 
	maxnoofAoIs, 
	maxnoofBPLMNs, 
	maxnoofCAGs, 
	maxnoofCAGsperPLMN, 
	maxnoofCellsinAoI, 
	maxnoofCellsinNG-RANnode, 
	maxnoofCellsinRNA, 
	maxnoofCellsinUEHistoryInfo, 
	maxnoofCellsUEMovingTrajectory, 
	maxnoofDRBs, 
	maxnoofEPLMNs, 
	maxnoofEPLMNsplus1, 
	maxnoofEUTRABands, 
	maxnoofEUTRABPLMNs, 
	maxnoofForbiddenTACs, 
	maxnoofMBSFNEUTRA, 
	maxnoofMultiConnectivityMinusOne, 
	maxnoofNeighbours, 
	maxnoofNIDs, 
	maxnoofNRCellBands, 
	maxnoofPDUSessions, 
	maxnoofPLMNs, 
	maxnoofProtectedResourcePatterns, 
	maxnoofQoSFlows, 
	maxnoofQoSParaSets, 
	maxnoofRANAreaCodes, 
	maxnoofRANAreasinRNA, 
	maxnoofSCellGroups, 
	maxnoofSCellGroupsplus1, 
	maxnoofSliceItems, 
	maxnoofExtSliceItems, 
	maxnoofSNPNIDs, 
	maxnoofsupportedTACs, 
	maxnoofsupportedPLMNs, 
	maxnoofTAI, 
	maxnoofTAIsinAoI, 
	maxnoofTNLAssociations, 
	maxnoofUEContexts, 
	maxNRARFCN, 
	maxNrOfErrors, 
	maxnoofRANNodesinAoI, 
	maxnooftimeperiods, 
	maxnoofslots, 
	maxnoofExtTLAs, 
	maxnoofGTPTLAs, 
	maxnoofCHOcells, 
	maxnoofPC5QoSFlows, 
	maxnoofSSBAreas, 
	maxnoofNRSCSs, 
	maxnoofPhysicalResourceBlocks, 
	maxnoofRACHReports, 
	maxnoofAdditionalPDCPDuplicationTNL, 
	maxnoofRLCDuplicationstate, 
	maxnoofBluetoothName, 
	maxnoofCellIDforMDT, 
	maxnoofMDTPLMNs, 
	maxnoofTAforMDT, 
	maxnoofWLANName, 
	maxnoofSensorName, 
	maxnoofNeighPCIforMDT, 
	maxnoofFreqforMDT

FROM XnAP-Constants

	Criticality, 
	ProcedureCode, 
	ProtocolIE-ID, 
	TriggeringMessage
FROM XnAP-CommonDataTypes

	ProtocolExtensionContainer{}, 
	ProtocolIE-Single-Container{}, 
	
	XNAP-PROTOCOL-EXTENSION, 
	XNAP-PROTOCOL-IES
FROM XnAP-Containers;


Additional-PDCP-Duplication-TNL-List ::= SEQUENCE (SIZE(1..maxnoofAdditionalPDCPDuplicationTNL)) OF Additional-PDCP-Duplication-TNL-Item
Additional-PDCP-Duplication-TNL-Item ::= SEQUENCE {
	additional-PDCP-Duplication-UP-TNL-Information	UPTransportLayerInformation, 
	iE-Extensions		ProtocolExtensionContainer { { Additional-PDCP-Duplication-TNL-ExtIEs} } 	OPTIONAL, 
	...
}
Additional-PDCP-Duplication-TNL-ExtIEs XNAP-PROTOCOL-EXTENSION ::= {
	...
}

Additional-UL-NG-U-TNLatUPF-Item ::= SEQUENCE {
	additional-UL-NG-U-TNLatUPF				UPTransportLayerInformation, 
	iE-Extensions		ProtocolExtensionContainer { { Additional-UL-NG-U-TNLatUPF-Item-ExtIEs} }	OPTIONAL, 
	...
}

Additional-UL-NG-U-TNLatUPF-Item-ExtIEs XNAP-PROTOCOL-EXTENSION ::= {
	...
}

Additional-UL-NG-U-TNLatUPF-List ::= SEQUENCE (SIZE(1..maxnoofMultiConnectivityMinusOne)) OF Additional-UL-NG-U-TNLatUPF-Item

ActivationIDforCellActivation	::= INTEGER (0..255)


AllocationandRetentionPriority ::= SEQUENCE {
	priorityLevel					INTEGER (0..15, ...), 
	pre-emption-capability			ENUMERATED {shall-not-trigger-preemptdatDion,  may-trigger-preemption,  ...}, 
	pre-emption-vulnerability		ENUMERATED {not-preemptable,  preemptable,  ...}, 
	iE-Extensions					ProtocolExtensionContainer { {AllocationandRetentionPriority-ExtIEs} } OPTIONAL, 
	...
}

AllocationandRetentionPriority-ExtIEs XNAP-PROTOCOL-EXTENSION ::= {
	...
}


ActivationSFN ::= INTEGER (0..1023)

AllowedCAG-ID-List-perPLMN ::= SEQUENCE (SIZE(1..maxnoofCAGsperPLMN)) OF CAG-Identifier

AllowedPNI-NPN-ID-List ::= SEQUENCE (SIZE(1..maxnoofEPLMNsplus1)) OF AllowedPNI-NPN-ID-Item

AllowedPNI-NPN-ID-Item ::= SEQUENCE {
	plmn-id								PLMN-Identity, 
	pni-npn-restricted-information		PNI-NPN-Restricted-Information, 
	allowed-CAG-id-list-per-plmn		AllowedCAG-ID-List-perPLMN, 
	iE-Extensions						ProtocolExtensionContainer { {AllowedPNI-NPN-ID-Item-ExtIEs} } OPTIONAL, 
	...
}

AllowedPNI-NPN-ID-Item-ExtIEs XNAP-PROTOCOL-EXTENSION ::= {
	...
}

AlternativeQoSParaSetList ::= SEQUENCE (SIZE(1..maxnoofQoSParaSets)) OF AlternativeQoSParaSetItem

AlternativeQoSParaSetItem ::= SEQUENCE {
	alternativeQoSParaSetIndex			QoSParaSetIndex, 
	guaranteedFlowBitRateDL				BitRate					OPTIONAL, 
	guaranteedFlowBitRateUL				BitRate					OPTIONAL, 
	packetDelayBudget					PacketDelayBudget		OPTIONAL, 
	packetErrorRate						PacketErrorRate			OPTIONAL, 
	iE-Extensions		ProtocolExtensionContainer { {AlternativeQoSParaSetItem-ExtIEs} }	OPTIONAL, 
	...
}

AlternativeQoSParaSetItem-ExtIEs XNAP-PROTOCOL-EXTENSION ::= {
	...
}


AMF-Region-Information ::= SEQUENCE (SIZE (1..maxnoofAMFRegions)) OF GlobalAMF-Region-Information

GlobalAMF-Region-Information ::= SEQUENCE {
	plmn-ID				PLMN-Identity, 
	amf-region-id		BIT STRING (SIZE (8)), 
	iE-Extensions					ProtocolExtensionContainer { {GlobalAMF-Region-Information-ExtIEs} } OPTIONAL, 
	...
}

GlobalAMF-Region-Information-ExtIEs XNAP-PROTOCOL-EXTENSION ::= {
	...
}


AMF-UE-NGAP-ID ::= INTEGER (0..1099511627775)


AreaOfInterestInformation ::= SEQUENCE (SIZE(1..maxnoofAoIs)) OF AreaOfInterest-Item

AreaOfInterest-Item ::= SEQUENCE {
	listOfTAIsinAoI					ListOfTAIsinAoI												OPTIONAL, 
	listOfCellsinAoI				ListOfCells													OPTIONAL, 
	listOfRANNodesinAoI				ListOfRANNodesinAoI											OPTIONAL, 
	requestReferenceID	RequestReferenceID, 
	iE-Extensions					ProtocolExtensionContainer { {AreaOfInterest-Item-ExtIEs} } OPTIONAL, 
	...
}

AreaOfInterest-Item-ExtIEs XNAP-PROTOCOL-EXTENSION ::= {
	...
}


AreaScopeOfMDT-NR ::= CHOICE {	
	cellBased					CellBasedMDT-NR, 
	tABased						TABasedMDT, 
	tAIBased					TAIBasedMDT, 
	...
}
AreaScopeOfMDT-EUTRA ::= CHOICE {	
	cellBased					CellBasedMDT-EUTRA, 
	tABased						TABasedMDT, 
	tAIBased					TAIBasedMDT, 
	...
}


AreaScopeOfNeighCellsList ::= SEQUENCE (SIZE(1..maxnoofFreqforMDT)) OF AreaScopeOfNeighCellsItem
AreaScopeOfNeighCellsItem ::= SEQUENCE {
	nrFrequencyInfo				NRFrequencyInfo, 
	pciListForMDT				PCIListForMDT		OPTIONAL, 
	iE-Extensions		ProtocolExtensionContainer { { AreaScopeOfNeighCellsItem-ExtIEs} }	OPTIONAL, 
	...
}

AreaScopeOfNeighCellsItem-ExtIEs XNAP-PROTOCOL-EXTENSION ::= {
	...
}

AS-SecurityInformation ::= SEQUENCE {
	key-NG-RAN-Star					BIT STRING (SIZE(256)), 
	ncc								INTEGER (0..7), 
	iE-Extensions					ProtocolExtensionContainer { {AS-SecurityInformation-ExtIEs} } OPTIONAL, 
	...
}

AS-SecurityInformation-ExtIEs XNAP-PROTOCOL-EXTENSION ::= {
	...
}


AssistanceDataForRANPaging ::= SEQUENCE {
	ran-paging-attempt-info			RANPagingAttemptInfo	OPTIONAL, 
	iE-Extensions					ProtocolExtensionContainer { {AssistanceDataForRANPaging-ExtIEs} } OPTIONAL, 
	...
}

AssistanceDataForRANPaging-ExtIEs XNAP-PROTOCOL-EXTENSION ::= {
	{ ID id-NPNPagingAssistanceInformation	CRITICALITY ignore	EXTENSION NPNPagingAssistanceInformation	PRESENCE optional }, 
	...
}


AvailableCapacity ::= INTEGER (1.. 100, ...)


AvailableRRCConnectionCapacityValue ::= INTEGER (0..100)


AveragingWindow ::= INTEGER (0..4095,  ...)


BluetoothMeasurementConfiguration ::= SEQUENCE {
	bluetoothMeasConfig             BluetoothMeasConfig, 
	bluetoothMeasConfigNameList		BluetoothMeasConfigNameList     OPTIONAL, 
	bt-rssi                         ENUMERATED {true,  ...}          OPTIONAL, 
	iE-Extensions		ProtocolExtensionContainer { { BluetoothMeasurementConfiguration-ExtIEs } } OPTIONAL, 
	...
}

BluetoothMeasurementConfiguration-ExtIEs XNAP-PROTOCOL-EXTENSION ::= {
	...
}

BluetoothMeasConfigNameList ::= SEQUENCE (SIZE(1..maxnoofBluetoothName)) OF BluetoothName

BluetoothMeasConfig::= ENUMERATED {setup, ...}

BluetoothName ::= OCTET STRING (SIZE (1..248))


BPLMN-ID-Info-EUTRA ::= SEQUENCE (SIZE(1..maxnoofEUTRABPLMNs)) OF BPLMN-ID-Info-EUTRA-Item

BPLMN-ID-Info-EUTRA-Item ::= SEQUENCE {
	broadcastPLMNs					BroadcastEUTRAPLMNs, 
	tac								TAC, 
	e-utraCI						E-UTRA-Cell-Identity, 
	ranac							RANAC OPTIONAL,  
	iE-Extension					ProtocolExtensionContainer { {BPLMN-ID-Info-EUTRA-Item-ExtIEs} } OPTIONAL, 
	...
}

BPLMN-ID-Info-EUTRA-Item-ExtIEs XNAP-PROTOCOL-EXTENSION ::= {
	...
}

BPLMN-ID-Info-NR ::= SEQUENCE (SIZE(1..maxnoofBPLMNs)) OF BPLMN-ID-Info-NR-Item

BPLMN-ID-Info-NR-Item ::= SEQUENCE {
	broadcastPLMNs					BroadcastPLMNs, 
	tac								TAC, 
	nr-CI							NR-Cell-Identity, 
	ranac							RANAC OPTIONAL,  
	iE-Extension					ProtocolExtensionContainer { {BPLMN-ID-Info-NR-Item-ExtIEs} } OPTIONAL, 
	...
}

BPLMN-ID-Info-NR-Item-ExtIEs XNAP-PROTOCOL-EXTENSION ::= {
	{ ID id-NPN-Broadcast-Information	CRITICALITY reject	EXTENSION NPN-Broadcast-Information		PRESENCE optional }, 
	...
}

BitRate	::= INTEGER (0..4000000000000, ...)



BroadcastCAG-Identifier-List ::= SEQUENCE (SIZE(1..maxnoofCAGs)) OF BroadcastCAG-Identifier-Item

BroadcastCAG-Identifier-Item ::= SEQUENCE {
	cag-Identifier					CAG-Identifier, 
	iE-Extension					ProtocolExtensionContainer { {BroadcastCAG-Identifier-Item-ExtIEs} } OPTIONAL, 
	...
}

BroadcastCAG-Identifier-Item-ExtIEs XNAP-PROTOCOL-EXTENSION ::= {
	...
}


BroadcastNID-List ::= SEQUENCE (SIZE(1..maxnoofNIDs)) OF BroadcastNID-Item

BroadcastNID-Item ::= SEQUENCE {
	nid							NID, 
	iE-Extension				ProtocolExtensionContainer { {BroadcastNID-Item-ExtIEs} } OPTIONAL, 
	...
}

BroadcastNID-Item-ExtIEs XNAP-PROTOCOL-EXTENSION ::= {
	...
}

BroadcastPLMNs ::= SEQUENCE (SIZE(1..maxnoofBPLMNs)) OF PLMN-Identity

BroadcastEUTRAPLMNs ::= SEQUENCE (SIZE(1..maxnoofEUTRABPLMNs)) OF PLMN-Identity


BroadcastPLMNinTAISupport-Item ::= SEQUENCE {
	plmn-id							PLMN-Identity, 
	tAISliceSupport-List			SliceSupport-List, 
	iE-Extension					ProtocolExtensionContainer { {BroadcastPLMNinTAISupport-Item-ExtIEs} } OPTIONAL, 
	...
}

BroadcastPLMNinTAISupport-Item-ExtIEs XNAP-PROTOCOL-EXTENSION ::= {
	{ID id-NPN-Support	CRITICALITY reject	EXTENSION NPN-Support		PRESENCE optional}|
	{ ID id-ExtendedTAISliceSupportList		CRITICALITY reject	EXTENSION ExtendedSliceSupportList		PRESENCE optional}, 
	...
}


BroadcastPNI-NPN-ID-Information ::= SEQUENCE (SIZE(1..maxnoofBPLMNs)) OF BroadcastPNI-NPN-ID-Information-Item

BroadcastPNI-NPN-ID-Information-Item ::= SEQUENCE {
	plmn-id							PLMN-Identity, 
	broadcastCAG-Identifier-List	BroadcastCAG-Identifier-List, 
	iE-Extension					ProtocolExtensionContainer { {BroadcastPNI-NPN-ID-Information-Item-ExtIEs} } OPTIONAL, 
	...
}


BroadcastPNI-NPN-ID-Information-Item-ExtIEs XNAP-PROTOCOL-EXTENSION ::= {
	...
}


BroadcastSNPNID-List ::= SEQUENCE (SIZE(1..maxnoofSNPNIDs)) OF BroadcastSNPNID


BroadcastSNPNID ::= SEQUENCE {
	plmn-id							PLMN-Identity, 
	broadcastNID-List								BroadcastNID-List, 
	iE-Extension					ProtocolExtensionContainer { {BroadcastSNPNID-ExtIEs} } OPTIONAL, 
	...
}

BroadcastSNPNID-ExtIEs XNAP-PROTOCOL-EXTENSION ::= {
	...
}



CAG-Identifier	::= BIT STRING (SIZE (32))


CapacityValue ::= INTEGER (0..100)



CapacityValueInfo ::= SEQUENCE {
	capacityValue				CapacityValue, 
	ssbAreaCapacityValueList 	SSBAreaCapacityValue-List, 
iE-Extension 				ProtocolExtensionContainer { {CapacityValueInfo-ExtIEs} } OPTIONAL, 
	...
}

CapacityValueInfo-ExtIEs XNAP-PROTOCOL-EXTENSION ::= {
	...
}


Cause ::= CHOICE {
	radioNetwork		CauseRadioNetworkLayer, 
	transport			CauseTransportLayer, 
	protocol			CauseProtocol, 
	misc				CauseMisc, 
	choice-extension	ProtocolIE-Single-Container { {Cause-ExtIEs} }
}

Cause-ExtIEs XNAP-PROTOCOL-IES ::= {
	...
}

CauseRadioNetworkLayer ::= ENUMERATED {
	cell-not-available, 
	handover-desirable-for-radio-reasons, 
	handover-target-not-allowed, 
	invalid-AMF-Set-ID, 
	no-radio-resources-available-in-target-cell, 
	partial-handover, 
	reduce-load-in-serving-cell, 
	resource-optimisation-handover, 
	time-critical-handover, 
	tXnRELOCoverall-expiry, 
	tXnRELOCprep-expiry, 
	unknown-GUAMI-ID, 
	unknown-local-NG-RAN-node-UE-XnAP-ID, 
	inconsistent-remote-NG-RAN-node-UE-XnAP-ID, 
	encryption-and-or-integrity-protection-algorithms-not-supported, 
	protection-algorithms-not-supported, 
	multiple-PDU-session-ID-instances, 
	unknown-PDU-session-ID, 
	unknown-QoS-Flow-ID, 
	multiple-QoS-Flow-ID-instances, 
	switch-off-ongoing, 
	not-supported-5QI-value, 
	tXnDCoverall-expiry, 
	tXnDCprep-expiry, 
	action-desirable-for-radio-reasons, 
	reduce-load, 
	resource-optimisation, 
	time-critical-action, 
	target-not-allowed, 
	no-radio-resources-available, 
	invalid-QoS-combination, 
	encryption-algorithms-not-supported, 
	procedure-cancelled, 
	rRM-purpose, 
	improve-user-bit-rate, 
	user-inactivity, 
	radio-connection-with-UE-lost, 
	failure-in-the-radio-interface-procedure, 
	bearer-option-not-supported, 
	up-integrity-protection-not-possible, 
	up-confidentiality-protection-not-possible, 
	resources-not-available-for-the-slice-s, 
	ue-max-IP-data-rate-reason, 
	cP-integrity-protection-failure, 
	uP-integrity-protection-failure, 
	slice-not-supported-by-NG-RAN, 
	mN-Mobility, 
	sN-Mobility, 
	count-reaches-max-value, 
	unknown-old-NG-RAN-node-UE-XnAP-ID, 
	pDCP-Overload, 
	drb-id-not-available, 
	unspecified, 
	..., 
	ue-context-id-not-known, 
	non-relocation-of-context, 
	cho-cpc-resources-tobechanged, 
	rSN-not-available-for-the-UP, 
	npn-access-denied
}

CauseTransportLayer ::= ENUMERATED {
	transport-resource-unavailable, 
	unspecified, 
	...
}

CauseProtocol ::= ENUMERATED {
	transfer-syntax-error, 
	abstract-syntax-error-reject, 
	abstract-syntax-error-ignore-and-notify, 
	message-not-compatible-with-receiver-state, 
	semantic-error, 
	abstract-syntax-error-falsely-constructed-message, 
	unspecified, 
	...
}

CauseMisc ::= ENUMERATED {
	control-processing-overload, 
	hardware-failure, 
	o-and-M-intervention, 
	not-enough-user-plane-processing-resources, 
	unspecified, 
	...
}

CellAssistanceInfo-NR	::= CHOICE {
	limitedNR-List				SEQUENCE (SIZE(1..maxnoofCellsinNG-RANnode)) OF NR-CGI, 
	full-List					ENUMERATED {all-served-cells-NR,  ...}, 
	choice-extension			ProtocolIE-Single-Container { {CellAssistanceInfo-NR-ExtIEs} }
}

CellAssistanceInfo-NR-ExtIEs XNAP-PROTOCOL-IES ::= {
	...
}

CellAndCapacityAssistanceInfo-NR	::= SEQUENCE {
	maximumCellListSize					MaximumCellListSize								OPTIONAL, 
	cellAssistanceInfo-NR		CellAssistanceInfo-NR 				OPTIONAL, 
	iE-Extensions						ProtocolExtensionContainer { { CellAndCapacityAssistanceInfo-NR-ExtIEs} }	OPTIONAL, 
	...
}


CellAndCapacityAssistanceInfo-NR-ExtIEs XNAP-PROTOCOL-EXTENSION ::= {
	...
}

CellAndCapacityAssistanceInfo-EUTRA	::= SEQUENCE {
	maximumCellListSize					MaximumCellListSize								OPTIONAL, 
	cellAssistanceInfo-EUTRA			CellAssistanceInfo-EUTRA 				OPTIONAL, 
	iE-Extensions						ProtocolExtensionContainer { { CellAndCapacityAssistanceInfo-EUTRA-ExtIEs} }	OPTIONAL, 
	...
}


CellAndCapacityAssistanceInfo-EUTRA-ExtIEs XNAP-PROTOCOL-EXTENSION ::= {
	...
}


CellAssistanceInfo-EUTRA	::= CHOICE {
	limitedEUTRA-List			SEQUENCE (SIZE(1..maxnoofCellsinNG-RANnode)) OF E-UTRA-CGI, 
	full-List					ENUMERATED {all-served-cells-NR,  ...}, 
	choice-extension			ProtocolIE-Single-Container { {CellAssistanceInfo-EUTRA-ExtIEs} }
}

CellAssistanceInfo-EUTRA-ExtIEs XNAP-PROTOCOL-IES ::= {
	...
}

CellBasedMDT-NR::= SEQUENCE {
	cellIdListforMDT-NR	CellIdListforMDT-NR, 
	iE-Extensions		ProtocolExtensionContainer { {CellBasedMDT-NR-ExtIEs} } OPTIONAL, 
	...
}

CellBasedMDT-NR-ExtIEs XNAP-PROTOCOL-EXTENSION ::= {
	...
}

CellIdListforMDT-NR ::= SEQUENCE (SIZE(1..maxnoofCellIDforMDT)) OF NR-CGI

CellBasedMDT-EUTRA::= SEQUENCE {
	cellIdListforMDT-EUTRA	CellIdListforMDT-EUTRA, 
	iE-Extensions		ProtocolExtensionContainer { {CellBasedMDT-EUTRA-ExtIEs} } OPTIONAL, 
	...
}

CellBasedMDT-EUTRA-ExtIEs XNAP-PROTOCOL-EXTENSION ::= {
	...
}
CellIdListforMDT-EUTRA ::= SEQUENCE (SIZE(1..maxnoofCellIDforMDT)) OF E-UTRA-CGI


CellCapacityClassValue ::= INTEGER (1..100, ...)


CellGroupID ::= INTEGER (0..maxnoofSCellGroups)


CellMeasurementResult ::= SEQUENCE (SIZE(1..maxnoofCellsinNG-RANnode)) OF CellMeasurementResult-Item

CellMeasurementResult-Item	::= SEQUENCE {
	cell-ID								GlobalNG-RANCell-ID, 
radioResourceStatus					RadioResourceStatus              OPTIONAL, 
tNLCapacityIndicator					TNLCapacityIndicator          	 OPTIONAL, 
compositeAvailableCapacityGroup  	CompositeAvailableCapacityGroup  OPTIONAL, 
sliceAvailableCapacity          	 	SliceAvailableCapacity           OPTIONAL,  
numberofActiveUEs                	NumberofActiveUEs                OPTIONAL, 
rRCConnections                   	RRCConnections                   OPTIONAL, 
	iE-Extensions						ProtocolExtensionContainer { { CellMeasurementResult-Item-ExtIEs} }	OPTIONAL, 
	...
}


CellMeasurementResult-Item-ExtIEs XNAP-PROTOCOL-EXTENSION ::= {
	...
}


CellToReport ::= SEQUENCE (SIZE(1..maxnoofCellsinNG-RANnode)) OF CellToReport-Item

CellToReport-Item	::= SEQUENCE {
	cell-ID									GlobalNG-RANCell-ID, 
sSBToReport-List                        SSBToReport-List, 
sliceToReport-List                      SliceToReport-List, 
	iE-Extensions						ProtocolExtensionContainer { { CellToReport-Item-ExtIEs} }	OPTIONAL, 
	...
}


CellToReport-Item-ExtIEs XNAP-PROTOCOL-EXTENSION ::= {
	...
}


CompositeAvailableCapacityGroup ::= SEQUENCE {
	compositeAvailableCapacityDownlink		CompositeAvailableCapacity, 
	compositeAvailableCapacityUplink	 	CompositeAvailableCapacity, 
	iE-Extensions				ProtocolExtensionContainer { { CompositeAvailableCapacityGroup-ExtIEs} }	OPTIONAL, 
	...
}

CompositeAvailableCapacityGroup-ExtIEs XNAP-PROTOCOL-EXTENSION ::= {
	...
}

CompositeAvailableCapacity ::= SEQUENCE {
	cellCapacityClassValue	CellCapacityClassValue             OPTIONAL, 
	capacityValueInfo	     	CapacityValueInfo,
	iE-Extensions				ProtocolExtensionContainer { { CompositeAvailableCapacity-ExtIEs} }OPTIONAL, 
	...
}

CompositeAvailableCapacity-ExtIEs XNAP-PROTOCOL-EXTENSION ::= {
	...
}

CHO-MRDC-Indicator ::= ENUMERATED {true,  ...}


CHOtrigger ::= ENUMERATED {
	cho-initiation, 
	cho-replace, 
	...
}

CHOinformation-Req ::= SEQUENCE {
	cho-trigger						CHOtrigger, 
	targetNG-RANnodeUEXnAPID		NG-RANnodeUEXnAPID										OPTIONAL
		, 
	cHO-EstimatedArrivalProbability	CHO-Probability											OPTIONAL, 
	iE-Extensions					ProtocolExtensionContainer { { CHOinformation-Req-ExtIEs} }	OPTIONAL, 
	...
}

CHOinformation-Req-ExtIEs XNAP-PROTOCOL-EXTENSION ::={
	...
}


CHOinformation-Ack ::= SEQUENCE {
	requestedTargetCellGlobalID		Target-CGI, 
	maxCHOoperations				MaxCHOpreparations											OPTIONAL, 
	iE-Extensions					ProtocolExtensionContainer { { CHOinformation-Ack-ExtIEs} }	OPTIONAL, 
	...
}

CHOinformation-Ack-ExtIEs XNAP-PROTOCOL-EXTENSION ::={
	...
}


CHO-Probability ::= INTEGER (1..100)


Connectivity-Support		::= SEQUENCE {
	eNDC-Support			ENUMERATED {supported,  not-supported,  ...}, 
	iE-Extensions			ProtocolExtensionContainer { {Connectivity-Support-ExtIEs} }	OPTIONAL, 
	...
}

Connectivity-Support-ExtIEs XNAP-PROTOCOL-EXTENSION ::= {
	...
}


COUNT-PDCP-SN12 ::= SEQUENCE {
	pdcp-SN12						INTEGER (0..4095), 
	hfn-PDCP-SN12					INTEGER (0..1048575), 
	iE-Extensions					ProtocolExtensionContainer { {COUNT-PDCP-SN12-ExtIEs} }	OPTIONAL, 
	...
}

COUNT-PDCP-SN12-ExtIEs XNAP-PROTOCOL-EXTENSION ::= {
	...
}


COUNT-PDCP-SN18 ::= SEQUENCE {
	pdcp-SN18						INTEGER (0..262143), 
	hfn-PDCP-SN18					INTEGER (0..16383), 
	iE-Extensions					ProtocolExtensionContainer { {COUNT-PDCP-SN18-ExtIEs} }	OPTIONAL, 
	...
}

COUNT-PDCP-SN18-ExtIEs XNAP-PROTOCOL-EXTENSION ::= {
	...
}


CPTransportLayerInformation ::= CHOICE {
	endpointIPAddress			TransportLayerAddress, 
	choice-extension			ProtocolIE-Single-Container { {CPTransportLayerInformation-ExtIEs} }
}

CPTransportLayerInformation-ExtIEs XNAP-PROTOCOL-IES ::= {
	{ ID id-EndpointIPAddressAndPort		CRITICALITY reject	TYPE EndpointIPAddressAndPort		PRESENCE mandatory}, 
	...
}


CriticalityDiagnostics ::= SEQUENCE {
	procedureCode					ProcedureCode					OPTIONAL, 
	triggeringMessage				TriggeringMessage				OPTIONAL, 
	procedureCriticality			Criticality						OPTIONAL, 
	iEsCriticalityDiagnostics		CriticalityDiagnostics-IE-List	OPTIONAL, 
	iE-Extensions					ProtocolExtensionContainer { {CriticalityDiagnostics-ExtIEs} }	OPTIONAL, 
	...
}

CriticalityDiagnostics-ExtIEs XNAP-PROTOCOL-EXTENSION ::= {
	...
}

CriticalityDiagnostics-IE-List ::= SEQUENCE (SIZE (1..maxNrOfErrors)) OF
	SEQUENCE {
		iECriticality			Criticality, 
		iE-ID					ProtocolIE-ID, 
		typeOfError				TypeOfError, 
		iE-Extensions			ProtocolExtensionContainer { {CriticalityDiagnostics-IE-List-ExtIEs} } OPTIONAL, 
		...
}

CriticalityDiagnostics-IE-List-ExtIEs XNAP-PROTOCOL-EXTENSION ::= {
	...
}


C-RNTI ::= BIT STRING (SIZE(16))


CyclicPrefix-E-UTRA-DL ::= ENUMERATED {
	normal, 
	extended, 
	...
}


CyclicPrefix-E-UTRA-UL ::= ENUMERATED {
	normal, 
	extended, 
	...
}

CSI-RSTransmissionIndication ::= ENUMERATED {
	activated, 
	deactivated, 
	...
}



XnUAddressInfoperPDUSession-List ::= SEQUENCE (SIZE(1..maxnoofPDUSessions)) OF XnUAddressInfoperPDUSession-Item

XnUAddressInfoperPDUSession-Item ::= SEQUENCE {
	pduSession-ID			PDUSession-ID, 
	dataForwardingInfoFromTargetNGRANnode		DataForwardingInfoFromTargetNGRANnode										OPTIONAL, 
	pduSessionResourceSetupCompleteInfo-SNterm			PDUSessionResourceBearerSetupCompleteInfo-SNterminated		OPTIONAL, 
	iE-Extension			ProtocolExtensionContainer { { XnUAddressInfoperPDUSession-Item-ExtIEs} }					OPTIONAL, 
	...
}

XnUAddressInfoperPDUSession-Item-ExtIEs XNAP-PROTOCOL-EXTENSION ::= {
{ ID id-SecondarydataForwardingInfoFromTarget-List	CRITICALITY ignore	EXTENSION SecondarydataForwardingInfoFromTarget-List	PRESENCE optional}|
{ ID id-DRB-IDs-takenintouse						CRITICALITY reject	EXTENSION DRB-List												PRESENCE optional}, 
	...
}

DataForwardingAccepted	::= ENUMERATED {data-forwarding-accepted,  ...}


DataForwardingInfoFromTargetNGRANnode ::= SEQUENCE {
	qosFlowsAcceptedForDataForwarding-List			QoSFLowsAcceptedToBeForwarded-List, 
	pduSessionLevelDLDataForwardingInfo				UPTransportLayerInformation								OPTIONAL, 
	pduSessionLevelULDataForwardingInfo				UPTransportLayerInformation								OPTIONAL, 
	dataForwardingResponseDRBItemList				DataForwardingResponseDRBItemList						OPTIONAL, 
	iE-Extension		ProtocolExtensionContainer { {DataForwardingInfoFromTargetNGRANnode-ExtIEs} }	OPTIONAL, 
	...
}

DataForwardingInfoFromTargetNGRANnode-ExtIEs XNAP-PROTOCOL-EXTENSION ::= {
	...
}


QoSFLowsAcceptedToBeForwarded-List ::= SEQUENCE (SIZE(1.. maxnoofQoSFlows)) OF QoSFLowsAcceptedToBeForwarded-Item

QoSFLowsAcceptedToBeForwarded-Item ::= SEQUENCE {
	qosFlowIdentifier			QoSFlowIdentifier, 
	iE-Extension				ProtocolExtensionContainer { {QoSFLowsAcceptedToBeForwarded-Item-ExtIEs} }	OPTIONAL, 
	...
}

QoSFLowsAcceptedToBeForwarded-Item-ExtIEs XNAP-PROTOCOL-EXTENSION ::= {
	...
}


DataforwardingandOffloadingInfofromSource ::= SEQUENCE {
	qosFlowsToBeForwarded			QoSFLowsToBeForwarded-List, 
	sourceDRBtoQoSFlowMapping		DRBToQoSFlowMapping-List													OPTIONAL, 
	iE-Extension		ProtocolExtensionContainer { {DataforwardingandOffloadingInfofromSource-ExtIEs} }	OPTIONAL, 
	...
}

DataforwardingandOffloadingInfofromSource-ExtIEs XNAP-PROTOCOL-EXTENSION ::= {
	...
}

QoSFLowsToBeForwarded-List ::= SEQUENCE (SIZE(1.. maxnoofQoSFlows)) OF QoSFLowsToBeForwarded-Item

QoSFLowsToBeForwarded-Item ::= SEQUENCE {
	qosFlowIdentifier			QoSFlowIdentifier, 
	dl-dataforwarding			DLForwarding, 
	ul-dataforwarding			ULForwarding, 
	iE-Extension		ProtocolExtensionContainer { {QoSFLowsToBeForwarded-Item-ExtIEs} }	OPTIONAL, 
	...
}

QoSFLowsToBeForwarded-Item-ExtIEs XNAP-PROTOCOL-EXTENSION ::= {
{ ID id-ULForwardingProposal	CRITICALITY ignore	EXTENSION ULForwardingProposal	PRESENCE optional }, 
	...
}



DataForwardingResponseDRBItemList ::= SEQUENCE (SIZE(1..maxnoofDRBs)) OF DataForwardingResponseDRBItem

DataForwardingResponseDRBItem ::= SEQUENCE {
	drb-ID				DRB-ID, 
	dlForwardingUPTNL	UPTransportLayerInformation												OPTIONAL, 
	ulForwardingUPTNL	UPTransportLayerInformation												OPTIONAL, 
	iE-Extension		ProtocolExtensionContainer { {DataForwardingResponseDRBItem-ExtIEs} }	OPTIONAL, 
	...
}

DataForwardingResponseDRBItem-ExtIEs XNAP-PROTOCOL-EXTENSION ::= {
	...
}


DataTrafficResources ::= BIT STRING (SIZE(6..17600))


DataTrafficResourceIndication ::= SEQUENCE {
	activationSFN					ActivationSFN, 
	sharedResourceType				SharedResourceType, 
	reservedSubframePattern			ReservedSubframePattern										OPTIONAL, 
	iE-Extension		ProtocolExtensionContainer { {DataTrafficResourceIndication-ExtIEs} }	OPTIONAL, 
	...
}

DataTrafficResourceIndication-ExtIEs XNAP-PROTOCOL-EXTENSION ::= {
	...
}


DAPSRequestInfo ::= SEQUENCE {
	dapsIndicator				ENUMERATED {daps-HO-required,  ...}, 
	iE-Extensions				ProtocolExtensionContainer { {DAPSRequestInfo-ExtIEs} } OPTIONAL, 
	...
}

DAPSRequestInfo-ExtIEs XNAP-PROTOCOL-EXTENSION ::= {
	...
}


DAPSResponseInfo-List ::= SEQUENCE (SIZE (1..maxnoofDRBs)) OF DAPSResponseInfo-Item

DAPSResponseInfo-Item ::= SEQUENCE {
	drbID						DRB-ID, 
	dapsResponseIndicator		ENUMERATED {daps-HO-accepted,  daps-HO-not-accepted,  ...}, 
	iE-Extensions				ProtocolExtensionContainer { {DAPSResponseInfo-Item-ExtIEs} } OPTIONAL, 
	...
}

DAPSResponseInfo-Item-ExtIEs XNAP-PROTOCOL-EXTENSION ::= {
	...
}


DeliveryStatus	::= INTEGER (0..4095,  ...)


DesiredActNotificationLevel	::= ENUMERATED {none,  qos-flow,  pdu-session,  ue-level,  ...}

DefaultDRB-Allowed ::= ENUMERATED {true,  false,  ...}


DLCountChoice ::= CHOICE {
	count12bits				COUNT-PDCP-SN12, 
	count18bits				COUNT-PDCP-SN18, 
	choice-extension		ProtocolIE-Single-Container { {DLCountChoice-ExtIEs} }
}

DLCountChoice-ExtIEs XNAP-PROTOCOL-IES ::= {
	...
}


DLForwarding	::= ENUMERATED {dl-forwarding-proposed,  ...}


DL-GBR-PRB-usage::= INTEGER (0..100)


DL-non-GBR-PRB-usage::= INTEGER (0..100)


DL-Total-PRB-usage::= INTEGER (0..100)


DRB-ID	::= INTEGER (1..32,  ...)


DRB-List ::= SEQUENCE (SIZE (1..maxnoofDRBs)) OF DRB-ID


DRB-List-withCause ::= SEQUENCE (SIZE (1..maxnoofDRBs)) OF DRB-List-withCause-Item

DRB-List-withCause-Item ::= SEQUENCE {
	drb-id		DRB-ID, 
	cause		Cause, 
	rLC-Mode	RLCMode								OPTIONAL, 
	iE-Extension		ProtocolExtensionContainer { {DRB-List-withCause-Item-ExtIEs} }	OPTIONAL, 
	...
}

DRB-List-withCause-Item-ExtIEs XNAP-PROTOCOL-EXTENSION ::= {
	...
}


DRB-Number ::= INTEGER (1..32,  ...)


DRBsSubjectToDLDiscarding-List ::= SEQUENCE (SIZE (1..maxnoofDRBs)) OF DRBsSubjectToDLDiscarding-Item

DRBsSubjectToDLDiscarding-Item ::= SEQUENCE {
	drbID				DRB-ID, 
	dlCount				DLCountChoice, 
	iE-Extension		ProtocolExtensionContainer { { DRBsSubjectToDLDiscarding-Item-ExtIEs} }	OPTIONAL, 
	...
}

DRBsSubjectToDLDiscarding-Item-ExtIEs XNAP-PROTOCOL-EXTENSION ::= {
	...
}


DRBsSubjectToEarlyStatusTransfer-List ::= SEQUENCE (SIZE (1..maxnoofDRBs)) OF DRBsSubjectToEarlyStatusTransfer-Item

DRBsSubjectToEarlyStatusTransfer-Item ::= SEQUENCE {
	drbID				DRB-ID, 
	dlCount				DLCountChoice, 
	iE-Extension		ProtocolExtensionContainer { { DRBsSubjectToEarlyStatusTransfer-Item-ExtIEs} }	OPTIONAL, 
	...
}

DRBsSubjectToEarlyStatusTransfer-Item-ExtIEs XNAP-PROTOCOL-EXTENSION ::= {
	...
}


DRBsSubjectToStatusTransfer-List ::= SEQUENCE (SIZE (1..maxnoofDRBs)) OF DRBsSubjectToStatusTransfer-Item

DRBsSubjectToStatusTransfer-Item ::= SEQUENCE {
	drbID				DRB-ID, 
	pdcpStatusTransfer-UL	DRBBStatusTransferChoice, 
	pdcpStatusTransfer-DL	DRBBStatusTransferChoice, 
	iE-Extension		ProtocolExtensionContainer { {DRBsSubjectToStatusTransfer-Item-ExtIEs} }	OPTIONAL, 
	...
}

DRBsSubjectToStatusTransfer-Item-ExtIEs XNAP-PROTOCOL-EXTENSION ::= {
	{ ID id-OldQoSFlowMap-ULendmarkerexpected	CRITICALITY reject		EXTENSION QoSFlows-List					PRESENCE optional }, 
	...
}


DRBBStatusTransferChoice ::= CHOICE {
	pdcp-sn-12bits		DRBBStatusTransfer12bitsSN, 
	pdcp-sn-18bits		DRBBStatusTransfer18bitsSN, 
	choice-extension		ProtocolIE-Single-Container { {DRBBStatusTransferChoice-ExtIEs} }
}

DRBBStatusTransferChoice-ExtIEs XNAP-PROTOCOL-IES ::= {
	...
}


DRBBStatusTransfer12bitsSN ::= SEQUENCE {
	receiveStatusofPDCPSDU	BIT STRING (SIZE(1..2048))											OPTIONAL, 
	cOUNTValue				COUNT-PDCP-SN12, 
	iE-Extension			ProtocolExtensionContainer { {DRBBStatusTransfer12bitsSN-ExtIEs} }	OPTIONAL, 
	...
}

DRBBStatusTransfer12bitsSN-ExtIEs XNAP-PROTOCOL-EXTENSION ::= {
	...
}


DRBBStatusTransfer18bitsSN ::= SEQUENCE {
	receiveStatusofPDCPSDU	BIT STRING (SIZE(1..131072))										OPTIONAL, 
	cOUNTValue				COUNT-PDCP-SN18, 
	iE-Extension			ProtocolExtensionContainer { {DRBBStatusTransfer18bitsSN-ExtIEs} }	OPTIONAL, 
	...
}

DRBBStatusTransfer18bitsSN-ExtIEs XNAP-PROTOCOL-EXTENSION ::= {
	...
}


DRBToQoSFlowMapping-List ::= SEQUENCE (SIZE (1..maxnoofDRBs)) OF DRBToQoSFlowMapping-Item

DRBToQoSFlowMapping-Item ::= SEQUENCE {
	drb-ID							DRB-ID, 
	qosFlows-List					QoSFlows-List, 
	rLC-Mode						RLCMode								OPTIONAL, 
	iE-Extension		ProtocolExtensionContainer { {DRBToQoSFlowMapping-Item-ExtIEs} }	OPTIONAL, 
	...
}

DRBToQoSFlowMapping-Item-ExtIEs XNAP-PROTOCOL-EXTENSION ::= {
	{ ID id-DAPSRequestInfo		CRITICALITY ignore		EXTENSION DAPSRequestInfo		PRESENCE optional  }, 
	...
}


DuplicationActivation ::= ENUMERATED {active,  inactive,  ...}


Dynamic5QIDescriptor ::= SEQUENCE {
	priorityLevelQoS			PriorityLevelQoS, 
	packetDelayBudget			PacketDelayBudget, 
	packetErrorRate				PacketErrorRate, 
	fiveQI						FiveQI													OPTIONAL, 
	delayCritical				ENUMERATED {delay-critical,  non-delay-critical,  ...}	OPTIONAL, 

	averagingWindow				AveragingWindow											OPTIONAL, 

	maximumDataBurstVolume		MaximumDataBurstVolume									OPTIONAL, 
	iE-Extension		ProtocolExtensionContainer { {Dynamic5QIDescriptor-ExtIEs } }	OPTIONAL, 
	...
}

Dynamic5QIDescriptor-ExtIEs XNAP-PROTOCOL-EXTENSION ::= {
	{ ID id-ExtendedPacketDelayBudget	CRITICALITY ignore	EXTENSION ExtendedPacketDelayBudget		PRESENCE optional}|
	{ ID id-CNPacketDelayBudgetDownlink		CRITICALITY ignore	EXTENSION ExtendedPacketDelayBudget		PRESENCE optional}|
	{ ID id-CNPacketDelayBudgetUplink		CRITICALITY ignore	EXTENSION ExtendedPacketDelayBudget		PRESENCE optional}, 
	...
}



E-RAB-ID		::= INTEGER (0..15,  ...)


E-UTRAARFCN ::= INTEGER (0..maxEARFCN)


E-UTRA-Cell-Identity			::= BIT STRING (SIZE(28))


E-UTRA-CGI ::= SEQUENCE {
	plmn-id				PLMN-Identity, 
	e-utra-CI			E-UTRA-Cell-Identity, 
	iE-Extension		ProtocolExtensionContainer { {E-UTRA-CGI-ExtIEs} } 	OPTIONAL, 
	...
}

E-UTRA-CGI-ExtIEs XNAP-PROTOCOL-EXTENSION ::= {
	...
}


E-UTRAFrequencyBandIndicator ::= INTEGER (1..256,  ...)


E-UTRAMultibandInfoList ::= SEQUENCE (SIZE(1..maxnoofEUTRABands)) OF E-UTRAFrequencyBandIndicator


E-UTRAPCI ::= INTEGER (0..503,  ...)


E-UTRAPRACHConfiguration ::= SEQUENCE {
	rootSequenceIndex						INTEGER (0..837), 
	zeroCorrelationIndex					INTEGER (0..15), 
	highSpeedFlag							ENUMERATED {true,  false,  ...}, 
	prach-FreqOffset						INTEGER (0..94), 
	prach-ConfigIndex						INTEGER (0..63)								OPTIONAL,  

	iE-Extensions							ProtocolExtensionContainer { {E-UTRAPRACHConfiguration-ExtIEs} }	OPTIONAL, 
	...
}

E-UTRAPRACHConfiguration-ExtIEs XNAP-PROTOCOL-EXTENSION ::= {
	...
}


E-UTRATransmissionBandwidth ::= ENUMERATED {bw6,  bw15,  bw25,  bw50,  bw75,  bw100,  ...,  bw1}

EndpointIPAddressAndPort ::=SEQUENCE {
	endpointIPAddress 				TransportLayerAddress, 
	portNumber						PortNumber, 
	iE-Extensions					ProtocolExtensionContainer { { EndpointIPAddressAndPort-ExtIEs} } OPTIONAL
}

EndpointIPAddressAndPort-ExtIEs XNAP-PROTOCOL-EXTENSION ::= {
	...
}


EventTriggered ::= SEQUENCE {
	loggedEventTriggeredConfig			LoggedEventTriggeredConfig, 
	iE-Extensions		ProtocolExtensionContainer { { EventTriggered-ExtIEs} } OPTIONAL, 
	...
}

EventTriggered-ExtIEs XNAP-PROTOCOL-EXTENSION ::= {
	...
}

EventType ::= ENUMERATED {
	report-upon-change-of-serving-cell, 
	report-UE-moving-presence-into-or-out-of-the-Area-of-Interest, 
	...
}


EventTypeTrigger ::= CHOICE {
	outOfCoverage					ENUMERATED {true,  ...}, 
	eventL1		EventL1, 
	choice-Extensions		ProtocolIE-Single-Container { {EventTypeTrigger-ExtIEs} }
}

EventTypeTrigger-ExtIEs XNAP-PROTOCOL-IES ::= {
	...
}

EventL1 ::= SEQUENCE {
	l1Threshold					MeasurementThresholdL1LoggedMDT, 
	hysteresis					Hysteresis, 
	timeToTrigger				TimeToTrigger, 
	iE-Extensions		ProtocolExtensionContainer { { EventL1-ExtIEs} } OPTIONAL, 
	...
}

EventL1-ExtIEs XNAP-PROTOCOL-EXTENSION ::= {
	...
}

MeasurementThresholdL1LoggedMDT ::= CHOICE {
	threshold-RSRP				Threshold-RSRP, 
	threshold-RSRQ				Threshold-RSRQ, 
	...
}

ExpectedActivityPeriod ::= INTEGER (1..30|40|50|60|80|100|120|150|180|181,  ...)

ExpectedHOInterval ::= ENUMERATED {
	sec15,  sec30,  sec60,  sec90,  sec120,  sec180,  long-time, 
	...
}

ExpectedIdlePeriod ::= INTEGER (1..30|40|50|60|80|100|120|150|180|181,  ...)

ExpectedUEActivityBehaviour ::= SEQUENCE {
	expectedActivityPeriod						ExpectedActivityPeriod						OPTIONAL, 
	expectedIdlePeriod							ExpectedIdlePeriod							OPTIONAL, 
	sourceOfUEActivityBehaviourInformation		SourceOfUEActivityBehaviourInformation		OPTIONAL, 
	iE-Extensions		ProtocolExtensionContainer { {ExpectedUEActivityBehaviour-ExtIEs} }	OPTIONAL, 
	...
}

ExpectedUEActivityBehaviour-ExtIEs XNAP-PROTOCOL-EXTENSION ::= {
	...
}

ExpectedUEBehaviour	::= SEQUENCE {
	expectedUEActivityBehaviour		ExpectedUEActivityBehaviour 					OPTIONAL, 
	expectedHOInterval				ExpectedHOInterval		 						OPTIONAL, 
	expectedUEMobility				ExpectedUEMobility								OPTIONAL, 
	expectedUEMovingTrajectory		ExpectedUEMovingTrajectory						OPTIONAL, 
	iE-Extensions		ProtocolExtensionContainer { {ExpectedUEBehaviour-ExtIEs} }	OPTIONAL, 
	...
}

ExpectedUEBehaviour-ExtIEs XNAP-PROTOCOL-EXTENSION ::= {
	...
}

ExpectedUEMobility ::= ENUMERATED {
	stationary, 
	mobile, 
	...
}

ExpectedUEMovingTrajectory ::= SEQUENCE (SIZE(1..maxnoofCellsUEMovingTrajectory)) OF ExpectedUEMovingTrajectoryItem

ExpectedUEMovingTrajectoryItem ::= SEQUENCE {
	nGRAN-CGI				GlobalNG-RANCell-ID, 
	timeStayedInCell		INTEGER (0..4095)													OPTIONAL, 
	iE-Extensions		ProtocolExtensionContainer { {ExpectedUEMovingTrajectoryItem-ExtIEs} }	OPTIONAL, 
	...
}

ExpectedUEMovingTrajectoryItem-ExtIEs XNAP-PROTOCOL-EXTENSION ::= {
	...
}

SourceOfUEActivityBehaviourInformation ::= ENUMERATED {
	subscription-information, 
	statistics, 
	...
}

ExtendedRATRestrictionInformation ::= SEQUENCE {
	primaryRATRestriction		BIT STRING (SIZE(8,  ...)), 
	secondaryRATRestriction		BIT STRING (SIZE(8,  ...)), 
	iE-Extensions		ProtocolExtensionContainer { {ExtendedRATRestrictionInformation-ExtIEs} }	OPTIONAL, 
	...
}

ExtendedRATRestrictionInformation-ExtIEs XNAP-PROTOCOL-EXTENSION ::= {
	...
}


ExtendedPacketDelayBudget ::= INTEGER (0..65535,  ...)

ExtendedSliceSupportList	::= SEQUENCE (SIZE(1..maxnoofExtSliceItems)) OF S-NSSAI

ExtTLAs ::= SEQUENCE (SIZE(1..maxnoofExtTLAs)) OF ExtTLA-Item

ExtTLA-Item ::= SEQUENCE {
	iPsecTLA							TransportLayerAddress		OPTIONAL, 
	gTPTransportLayerAddresses			GTPTLAs							OPTIONAL, 
	iE-Extensions		ProtocolExtensionContainer { {ExtTLA-Item-ExtIEs} } OPTIONAL, 
	...
}

ExtTLA-Item-ExtIEs XNAP-PROTOCOL-EXTENSION ::= {
	...
}


GTPTLAs	::= SEQUENCE (SIZE(1.. maxnoofGTPTLAs)) OF	GTPTLA-Item


GTPTLA-Item	::= SEQUENCE {
	gTPTransportLayerAddresses				TransportLayerAddress, 
	iE-Extensions	ProtocolExtensionContainer { { GTPTLA-Item-ExtIEs } }         OPTIONAL, 
	...
}

GTPTLA-Item-ExtIEs XNAP-PROTOCOL-EXTENSION ::= {
	...
}


FiveGCMobilityRestrictionListContainer ::= OCTET STRING


FiveQI ::= INTEGER (0..255,  ...)

FrequencyShift7p5khz ::= ENUMERATED {false,  true,  ...}



GBRQoSFlowInfo ::= SEQUENCE {
	maxFlowBitRateDL			BitRate, 
	maxFlowBitRateUL			BitRate, 
	guaranteedFlowBitRateDL		BitRate, 
	guaranteedFlowBitRateUL		BitRate, 
	notificationControl			ENUMERATED {notification-requested,  ...}				OPTIONAL, 
	maxPacketLossRateDL			PacketLossRate											OPTIONAL, 
	maxPacketLossRateUL			PacketLossRate											OPTIONAL, 
	iE-Extensions				ProtocolExtensionContainer { {GBRQoSFlowInfo-ExtIEs} }	OPTIONAL, 
	...
}

GBRQoSFlowInfo-ExtIEs XNAP-PROTOCOL-EXTENSION ::= {
{ ID id-AlternativeQoSParaSetList	CRITICALITY ignore	EXTENSION AlternativeQoSParaSetList	PRESENCE optional	}, 
	...
}

GlobalgNB-ID	::= SEQUENCE {
	plmn-id			PLMN-Identity, 
	gnb-id			GNB-ID-Choice, 
	iE-Extensions		ProtocolExtensionContainer { {GlobalgNB-ID-ExtIEs} } OPTIONAL, 
	...
}

GlobalgNB-ID-ExtIEs XNAP-PROTOCOL-EXTENSION ::= {
	...
}


GNB-ID-Choice ::= CHOICE {
	gnb-ID					BIT STRING (SIZE(22..32)), 
	choice-extension		ProtocolIE-Single-Container { {GNB-ID-Choice-ExtIEs} }
}

GNB-ID-Choice-ExtIEs XNAP-PROTOCOL-IES ::= {
	...
}


GNB-RadioResourceStatus	::= SEQUENCE {
	ssbAreaRadioResourceStatus-List				SSBAreaRadioResourceStatus-List, 
	iE-Extensions							ProtocolExtensionContainer { { GNB-RadioResourceStatus-ExtIEs} }, 
	...
}

GNB-RadioResourceStatus-ExtIEs XNAP-PROTOCOL-EXTENSION ::= {
	...
}

GlobalngeNB-ID	::= SEQUENCE {
	plmn-id			PLMN-Identity, 
	enb-id			ENB-ID-Choice, 
	iE-Extensions		ProtocolExtensionContainer { {GlobaleNB-ID-ExtIEs} } OPTIONAL, 
	...
}

GlobaleNB-ID-ExtIEs XNAP-PROTOCOL-EXTENSION ::= {
	...
}


ENB-ID-Choice ::= CHOICE {
	enb-ID-macro			BIT STRING (SIZE(20)), 
	enb-ID-shortmacro		BIT STRING (SIZE(18)), 
	enb-ID-longmacro		BIT STRING (SIZE(21)), 
	choice-extension		ProtocolIE-Single-Container { {ENB-ID-Choice-ExtIEs} }
}

ENB-ID-Choice-ExtIEs XNAP-PROTOCOL-IES ::= {
	...
}


GlobalNG-RANCell-ID	::= SEQUENCE {
	plmn-id					PLMN-Identity, 
	ng-RAN-Cell-id			NG-RAN-Cell-Identity, 
	iE-Extensions		ProtocolExtensionContainer { {GlobalNG-RANCell-ID-ExtIEs} } OPTIONAL, 
	...
}

GlobalNG-RANCell-ID-ExtIEs XNAP-PROTOCOL-EXTENSION ::= {
	...
}


GlobalNG-RANNode-ID ::= CHOICE {
	gNB						GlobalgNB-ID, 
	ng-eNB					GlobalngeNB-ID, 
	choice-extension		ProtocolIE-Single-Container { {GlobalNG-RANNode-ID-ExtIEs} }
}

GlobalNG-RANNode-ID-ExtIEs XNAP-PROTOCOL-IES ::= {
	...
}


GTP-TEID	::= OCTET STRING (SIZE(4))


GTPtunnelTransportLayerInformation ::= SEQUENCE {
	tnl-address			TransportLayerAddress, 
	gtp-teid			GTP-TEID, 
	iE-Extensions		ProtocolExtensionContainer { {GTPtunnelTransportLayerInformation-ExtIEs} } OPTIONAL, 
	...
}

GTPtunnelTransportLayerInformation-ExtIEs XNAP-PROTOCOL-EXTENSION ::= {
	...
}


GUAMI ::= SEQUENCE {
	plmn-ID				PLMN-Identity, 
	amf-region-id		BIT STRING (SIZE (8)), 
	amf-set-id			BIT STRING (SIZE (10)), 
	amf-pointer			BIT STRING (SIZE (6)), 
	iE-Extensions		ProtocolExtensionContainer { {GUAMI-ExtIEs} } OPTIONAL, 
	...
}

GUAMI-ExtIEs XNAP-PROTOCOL-EXTENSION ::= {
	...
}



HandoverReportType ::= ENUMERATED {
	hoTooEarly, 
	hoToWrongCell, 
	intersystempingpong, 
	...
}

Hysteresis ::=                      INTEGER (0..30)


IABNodeIndication ::= ENUMERATED {true, ...}

ImmediateMDT-EUTRA ::= OCTET STRING 


ImmediateMDT-NR ::= SEQUENCE { 
	measurementsToActivate		MeasurementsToActivate, 
	m1Configuration				M1Configuration				OPTIONAL, 
	m4Configuration				M4Configuration				OPTIONAL, 
	m5Configuration				M5Configuration				OPTIONAL, 
	mDT-Location-Info			MDT-Location-Info			OPTIONAL, 
	m6Configuration				M6Configuration				OPTIONAL, 
	m7Configuration				M7Configuration				OPTIONAL, 
	bluetoothMeasurementConfiguration				BluetoothMeasurementConfiguration				OPTIONAL, 
	wLANMeasurementConfiguration					WLANMeasurementConfiguration					OPTIONAL, 
	sensorMeasurementConfiguration					SensorMeasurementConfiguration					OPTIONAL, 
	iE-Extensions				ProtocolExtensionContainer { { ImmediateMDT-NR-ExtIEs} } OPTIONAL, 
	...
}

ImmediateMDT-NR-ExtIEs XNAP-PROTOCOL-EXTENSION ::= {
	...
}

InitiatingCondition-FailureIndication ::= CHOICE {
	rRCReestab					RRCReestab-initiated, 
	rRCSetup					RRCSetup-initiated, 
	choice-extension				ProtocolIE-Single-Container { {InitiatingCondition-FailureIndication-ExtIEs} }
}

InitiatingCondition-FailureIndication-ExtIEs XNAP-PROTOCOL-IES ::= {
	...
}

IntendedTDD-DL-ULConfiguration-NR ::= SEQUENCE {
	nrscs							NRSCS, 
	nrCyclicPrefix					NRCyclicPrefix, 
	nrDL-ULTransmissionPeriodicity	NRDL-ULTransmissionPeriodicity, 
	slotConfiguration-List			SlotConfiguration-List, 
	iE-Extensions					ProtocolExtensionContainer { {IntendedTDD-DL-ULConfiguration-NR-ExtIEs} }	OPTIONAL, 
	...
}

IntendedTDD-DL-ULConfiguration-NR-ExtIEs XNAP-PROTOCOL-EXTENSION ::= {
	...
}

InterfaceInstanceIndication ::= INTEGER (0..255,  ...)

InterfacesToTrace ::= BIT STRING { ng-c (0),  x-nc (1),  uu (2),  f1-c (3),  e1 (4)} (SIZE(8))


I-RNTI ::= CHOICE {
	i-RNTI-full			BIT STRING (SIZE(40)),  
	i-RNTI-short		BIT STRING (SIZE(24)), 
	choice-extension	ProtocolIE-Single-Container { {I-RNTI-ExtIEs} }
}

I-RNTI-ExtIEs XNAP-PROTOCOL-IES ::= {
	...
}





LastVisitedCell-Item ::= CHOICE {
	nG-RAN-Cell						LastVisitedNGRANCellInformation, 
	e-UTRAN-Cell					LastVisitedEUTRANCellInformation, 
	uTRAN-Cell						LastVisitedUTRANCellInformation, 
	gERAN-Cell						LastVisitedGERANCellInformation, 
	choice-extension				ProtocolIE-Single-Container { { LastVisitedCell-Item-ExtIEs} }
}

LastVisitedCell-Item-ExtIEs XNAP-PROTOCOL-IES ::= {
	...
}

LastVisitedEUTRANCellInformation ::= OCTET STRING

LastVisitedGERANCellInformation	::= OCTET STRING

LastVisitedNGRANCellInformation	::= OCTET STRING

LastVisitedUTRANCellInformation	::= OCTET STRING


LCID ::= INTEGER (1..32,  ...)

Links-to-log ::= ENUMERATED {uplink,  downlink,  both-uplink-and-downlink,  ...} 


ListOfCells ::= SEQUENCE (SIZE(1..maxnoofCellsinAoI)) OF CellsinAoI-Item

CellsinAoI-Item ::= SEQUENCE {
	pLMN-Identity			PLMN-Identity, 
	ng-ran-cell-id			NG-RAN-Cell-Identity, 
	iE-Extensions			ProtocolExtensionContainer { {CellsinAoI-Item-ExtIEs} } OPTIONAL, 
	...
}

CellsinAoI-Item-ExtIEs XNAP-PROTOCOL-EXTENSION ::= {
	...
}


ListOfRANNodesinAoI ::= SEQUENCE (SIZE(1.. maxnoofRANNodesinAoI)) OF GlobalNG-RANNodesinAoI-Item

GlobalNG-RANNodesinAoI-Item ::= SEQUENCE {
	global-NG-RAN-Node-ID		GlobalNG-RANNode-ID, 
	iE-Extensions		ProtocolExtensionContainer { {GlobalNG-RANNodesinAoI-Item-ExtIEs} } OPTIONAL, 
	...
}

GlobalNG-RANNodesinAoI-Item-ExtIEs XNAP-PROTOCOL-EXTENSION ::= {
	...
}


ListOfTAIsinAoI ::= SEQUENCE (SIZE(1..maxnoofTAIsinAoI)) OF TAIsinAoI-Item

TAIsinAoI-Item ::= SEQUENCE {
	pLMN-Identity		PLMN-Identity, 
	tAC					TAC, 
	iE-Extensions		ProtocolExtensionContainer { {TAIsinAoI-Item-ExtIEs} } OPTIONAL, 
	...
}

TAIsinAoI-Item-ExtIEs XNAP-PROTOCOL-EXTENSION ::= {
	...
}

LocationInformationSNReporting ::= ENUMERATED {
	pSCell, 
	...
}

LocationReportingInformation ::= SEQUENCE {
	eventType			EventType, 
	reportArea			ReportArea, 
	areaOfInterest		AreaOfInterestInformation			OPTIONAL, 
	iE-Extensions		ProtocolExtensionContainer { {LocationReportingInformation-ExtIEs} } OPTIONAL, 
	...
}

LocationReportingInformation-ExtIEs XNAP-PROTOCOL-EXTENSION ::={
	...
}


LoggedMDT-EUTRA ::= SEQUENCE {
	loggingInterval								LoggingInterval, 
	loggingDuration								LoggingDuration, 
	bluetoothMeasurementConfiguration			BluetoothMeasurementConfiguration		OPTIONAL, 
	wLANMeasurementConfiguration				WLANMeasurementConfiguration			OPTIONAL, 
	iE-Extensions				ProtocolExtensionContainer { {LoggedMDT-EUTRA-ExtIEs} } OPTIONAL, 
	...
}

LoggedMDT-EUTRA-ExtIEs	XNAP-PROTOCOL-EXTENSION ::= {
...
}

LoggedEventTriggeredConfig ::= SEQUENCE {
	eventTypeTrigger					EventTypeTrigger, 
	iE-Extensions		ProtocolExtensionContainer { { LoggedEventTriggeredConfig-ExtIEs} } OPTIONAL, 
	...
}

LoggedEventTriggeredConfig-ExtIEs XNAP-PROTOCOL-EXTENSION ::= {
	...
}

LoggedMDT-NR ::= SEQUENCE {
	loggingInterval						LoggingInterval, 
	loggingDuration						LoggingDuration, 
	reportType							ReportType, 
	bluetoothMeasurementConfiguration	BluetoothMeasurementConfiguration			OPTIONAL, 
	wLANMeasurementConfiguration		WLANMeasurementConfiguration				OPTIONAL, 
	sensorMeasurementConfiguration		SensorMeasurementConfiguration				OPTIONAL, 
	areaScopeOfNeighCellsList			AreaScopeOfNeighCellsList					OPTIONAL, 	iE-Extensions						ProtocolExtensionContainer { {LoggedMDT-NR-ExtIEs} } OPTIONAL, 
	...
}

LoggedMDT-NR-ExtIEs	XNAP-PROTOCOL-EXTENSION ::= {
...
}

LoggingInterval ::= ENUMERATED { ms320,  ms640,  ms1280,  ms2560,  ms5120,  ms10240,  ms20480,  ms30720,  ms40960,  ms61440}

LoggingDuration ::= ENUMERATED {m10,  m20,  m40,  m60,  m90,  m120}

LowerLayerPresenceStatusChange ::= ENUMERATED {
	release-lower-layers, 
	re-establish-lower-layers, 
	..., 
	suspend-lower-layers,  
	resume-lower-layers
}

LTEV2XServicesAuthorized ::= SEQUENCE {
	vehicleUE			VehicleUE											OPTIONAL, 
pedestrianUE 		PedestrianUE						OPTIONAL, 
	iE-Extensions		ProtocolExtensionContainer { {LTEV2XServicesAuthorized-ExtIEs} }	OPTIONAL, 
	...
}

LTEV2XServicesAuthorized-ExtIEs XNAP-PROTOCOL-EXTENSION ::= {
	...
}


LTEUESidelinkAggregateMaximumBitRate ::= SEQUENCE {
	uESidelinkAggregateMaximumBitRate		BitRate, 
	iE-Extensions					ProtocolExtensionContainer { {LTEUESidelinkAggregateMaximumBitRate-ExtIEs} } OPTIONAL, 
	...
}

LTEUESidelinkAggregateMaximumBitRate-ExtIEs XNAP-PROTOCOL-EXTENSION ::= {
	...
}



M1Configuration ::= SEQUENCE {
	m1reportingTrigger			M1ReportingTrigger, 
	m1thresholdeventA2			M1ThresholdEventA2				OPTIONAL, 

	m1periodicReporting			M1PeriodicReporting				OPTIONAL, 

	iE-Extensions				ProtocolExtensionContainer { { M1Configuration-ExtIEs} } OPTIONAL, 
	...
}

M1Configuration-ExtIEs XNAP-PROTOCOL-EXTENSION ::= {
	...
}


M1PeriodicReporting ::= SEQUENCE { 
	reportInterval				ReportIntervalMDT, 
	reportAmount				ReportAmountMDT, 
	iE-Extensions				ProtocolExtensionContainer { { M1PeriodicReporting-ExtIEs} } OPTIONAL, 
	...
}

M1PeriodicReporting-ExtIEs XNAP-PROTOCOL-EXTENSION ::= {
	...
}

M1ReportingTrigger ::= ENUMERATED{
	periodic, 
	a2eventtriggered, 
	a2eventtriggered-periodic, 
	...
	
}

M1ThresholdEventA2 ::= SEQUENCE { 
	measurementThreshold	MeasurementThresholdA2, 
	iE-Extensions			ProtocolExtensionContainer { { M1ThresholdEventA2-ExtIEs} } OPTIONAL, 
	...
}

M1ThresholdEventA2-ExtIEs XNAP-PROTOCOL-EXTENSION ::= {
	...
}



M4Configuration ::= SEQUENCE {
	m4period			M4period, 
	m4-links-to-log		Links-to-log, 
	iE-Extensions		ProtocolExtensionContainer { { M4Configuration-ExtIEs} } OPTIONAL, 
	...
}

M4Configuration-ExtIEs XNAP-PROTOCOL-EXTENSION ::= {
	...
}

M4period ::= ENUMERATED {ms1024,  ms2048,  ms5120,  ms10240,  min1,  ... } 

M5Configuration ::= SEQUENCE {
	m5period			M5period, 
	m5-links-to-log		Links-to-log, 
	iE-Extensions		ProtocolExtensionContainer { { M5Configuration-ExtIEs} } OPTIONAL, 
	...
}

M5Configuration-ExtIEs XNAP-PROTOCOL-EXTENSION ::= {
	...
}

M5period ::= ENUMERATED {ms1024,  ms2048,  ms5120,  ms10240,  min1,  ... } 

M6Configuration ::= SEQUENCE {
	m6report-Interval	M6report-Interval, 
	m6-links-to-log		Links-to-log, 
	iE-Extensions		ProtocolExtensionContainer { { M6Configuration-ExtIEs} } OPTIONAL, 
	...
}

M6Configuration-ExtIEs XNAP-PROTOCOL-EXTENSION ::= {
	...
}

M6report-Interval ::= ENUMERATED { ms120,  ms240,  ms480,  ms640,  ms1024,  ms2048,  ms5120,  ms10240,  ms20480,  ms40960,  min1,  min6,  min12,  min30, ... }


M7Configuration ::= SEQUENCE {
	m7period			M7period, 
	m7-links-to-log		Links-to-log, 
	iE-Extensions		ProtocolExtensionContainer { { M7Configuration-ExtIEs} } OPTIONAL, 
	...
}

M7Configuration-ExtIEs XNAP-PROTOCOL-EXTENSION ::= {
	...
}

M7period ::= INTEGER(1..60,  ...)


MAC-I ::= BIT STRING (SIZE(16))


MaskedIMEISV	::= BIT STRING (SIZE(64))


MaxCHOpreparations ::= INTEGER (1..8,  ...)


MaximumDataBurstVolume ::= INTEGER (0..4095,  ...,  4096.. 2000000)


MaximumIPdatarate ::= SEQUENCE {
	maxIPrate-UL			MaxIPrate, 
	iE-Extensions		ProtocolExtensionContainer { {MaximumIPdatarate-ExtIEs} }	OPTIONAL, 
	...
}

MaximumIPdatarate-ExtIEs XNAP-PROTOCOL-EXTENSION ::= {
{ ID id-MaxIPrate-DL	CRITICALITY ignore	EXTENSION MaxIPrate	PRESENCE optional}, 
	...
}

MaxIPrate ::= ENUMERATED {
	bitrate64kbs, 
	max-UErate, 
	...
}


MBSFNControlRegionLength ::= INTEGER (0..3)


MBSFNSubframeAllocation-E-UTRA ::= CHOICE {
	oneframe				BIT STRING (SIZE(6)), 
	fourframes				BIT STRING (SIZE(24)), 
	choice-extension		ProtocolIE-Single-Container { {MBSFNSubframeAllocation-E-UTRA-ExtIEs} }
}

MBSFNSubframeAllocation-E-UTRA-ExtIEs XNAP-PROTOCOL-IES ::= {
	...
}


MBSFNSubframeInfo-E-UTRA ::= SEQUENCE (SIZE(1..maxnoofMBSFNEUTRA)) OF MBSFNSubframeInfo-E-UTRA-Item


MBSFNSubframeInfo-E-UTRA-Item ::= SEQUENCE {
	radioframeAllocationPeriod		ENUMERATED{n1, n2, n4, n8, n16, n32, ...}, 
	radioframeAllocationOffset		INTEGER (0..7,  ...), 
	subframeAllocation				MBSFNSubframeAllocation-E-UTRA, 
	iE-Extensions					ProtocolExtensionContainer { {MBSFNSubframeInfo-E-UTRA-Item-ExtIEs} } OPTIONAL, 
	...
}

MBSFNSubframeInfo-E-UTRA-Item-ExtIEs XNAP-PROTOCOL-EXTENSION ::={
	...
}

MDT-Activation 	::= ENUMERATED { 
	immediate-MDT-only, 
	immediate-MDT-and-Trace, 
	logged-MDT-only, 
	...
}

MDT-Configuration ::= SEQUENCE {
	mDT-Configuration-NR		MDT-Configuration-NR		 OPTIONAL, 
	mDT-Configuration-EUTRA		MDT-Configuration-EUTRA		 OPTIONAL, 
iE-Extensions		ProtocolExtensionContainer { { MDT-Configuration-ExtIEs} } OPTIONAL, 
	...
}
MDT-Configuration-ExtIEs XNAP-PROTOCOL-EXTENSION ::= {
	...
}

MDT-Configuration-NR ::= SEQUENCE {
	mdt-Activation				MDT-Activation, 
	areaScopeOfMDT-NR			AreaScopeOfMDT-NR	OPTIONAL, 
	mDTMode-NR					MDTMode-NR, 
	signallingBasedMDTPLMNList	MDTPLMNList, 
	iE-Extensions		ProtocolExtensionContainer { { MDT-Configuration-NR-ExtIEs} } OPTIONAL, 
	...
}
MDT-Configuration-NR-ExtIEs XNAP-PROTOCOL-EXTENSION ::= {
	...
}

MDT-Configuration-EUTRA ::= SEQUENCE {
	mdt-Activation				MDT-Activation, 
	areaScopeOfMDT-EUTRA		AreaScopeOfMDT-EUTRA	OPTIONAL, 
	mDTMode-EUTRA				MDTMode-EUTRA, 
	signallingBasedMDTPLMNList	MDTPLMNList, 
	iE-Extensions		ProtocolExtensionContainer { { MDT-Configuration-EUTRA-ExtIEs} } OPTIONAL, 
	...
}
MDT-Configuration-EUTRA-ExtIEs XNAP-PROTOCOL-EXTENSION ::= {
	...
}


MDT-Location-Info ::= BIT STRING (SIZE (8))


MDTPLMNList ::= SEQUENCE (SIZE(1..maxnoofMDTPLMNs)) OF PLMN-Identity

MDTMode-NR ::= CHOICE {
	immediateMDT				ImmediateMDT-NR, 
	loggedMDT					LoggedMDT-NR, 
	..., 
	mDTMode-NR-Extension			MDTMode-NR-Extension
}

MDTMode-NR-Extension ::= ProtocolIE-Single-Container {{ MDTMode-NR-ExtensionIE }}

MDTMode-NR-ExtensionIE XNAP-PROTOCOL-IES ::= {
	...
}

MDTMode-EUTRA ::= CHOICE {
	immediateMDT				ImmediateMDT-EUTRA, 
	loggedMDT					LoggedMDT-EUTRA, 
	..., 
	mDTMode-EUTRA-Extension			MDTMode-EUTRA-Extension
}

MDTMode-EUTRA-Extension ::= ProtocolIE-Single-Container {{ MDTMode-EUTRA-ExtensionIE }}

MDTMode-EUTRA-ExtensionIE XNAP-PROTOCOL-IES ::= {
	...
}

MeasurementsToActivate ::= BIT STRING (SIZE (8))

MeasurementThresholdA2 ::= CHOICE {
	threshold-RSRP				Threshold-RSRP, 
	threshold-RSRQ				Threshold-RSRQ, 
	threshold-SINR				Threshold-SINR, 
	choice-extension	ProtocolIE-Single-Container { { MeasurementThresholdA2-ExtIEs} }
}

MeasurementThresholdA2-ExtIEs XNAP-PROTOCOL-IES ::= {
	...
}


Measurement-ID 	 ::= INTEGER (1..4095, ...)


MobilityInformation	 ::= BIT STRING (SIZE(32))

MobilityParametersModificationRange ::= SEQUENCE {
	handoverTriggerChangeLowerLimit		INTEGER (-20..20), 
	handoverTriggerChangeUpperLimit		INTEGER (-20..20), 
	...
}

MobilityParametersInformation ::= SEQUENCE {
	handoverTriggerChange			INTEGER (-20..20), 
	...
}


MobilityRestrictionList ::= SEQUENCE {
	serving-PLMN						PLMN-Identity, 
	equivalent-PLMNs					SEQUENCE (SIZE(1..maxnoofEPLMNs)) OF PLMN-Identity			OPTIONAL, 
	rat-Restrictions					RAT-RestrictionsList										OPTIONAL, 
	forbiddenAreaInformation			ForbiddenAreaList											OPTIONAL, 
	serviceAreaInformation				ServiceAreaList												OPTIONAL, 
	iE-Extensions		ProtocolExtensionContainer { {MobilityRestrictionList-ExtIEs} }				OPTIONAL, 
	...
}

MobilityRestrictionList-ExtIEs XNAP-PROTOCOL-EXTENSION ::={ 
{ ID id-LastE-UTRANPLMNIdentity					CRITICALITY ignore	EXTENSION PLMN-Identity									PRESENCE optional		}|
{ ID id-CNTypeRestrictionsForServing			CRITICALITY ignore	EXTENSION CNTypeRestrictionsForServing				PRESENCE optional		}|
{ ID id-CNTypeRestrictionsForEquivalent			CRITICALITY ignore	EXTENSION CNTypeRestrictionsForEquivalent			PRESENCE optional		}|
{ ID id-NPNMobilityInformation					CRITICALITY reject	EXTENSION NPNMobilityInformation						PRESENCE optional		}, 
	...
}

CNTypeRestrictionsForEquivalent ::= SEQUENCE (SIZE(1..maxnoofEPLMNs)) OF CNTypeRestrictionsForEquivalentItem

CNTypeRestrictionsForEquivalentItem ::= SEQUENCE {
	plmn-Identity						PLMN-Identity, 
	cn-Type								ENUMERATED {epc-forbidden,  fiveGC-forbidden,  ...}, 
	iE-Extensions						ProtocolExtensionContainer { {CNTypeRestrictionsForEquivalentItem-ExtIEs} }				OPTIONAL, 
	...
}

CNTypeRestrictionsForEquivalentItem-ExtIEs XNAP-PROTOCOL-EXTENSION ::={
	...
}

CNTypeRestrictionsForServing ::= ENUMERATED {
	epc-forbidden, 
	...
}

RAT-RestrictionsList ::= SEQUENCE (SIZE(1..maxnoofPLMNs)) OF RAT-RestrictionsItem


RAT-RestrictionsItem ::= SEQUENCE {
	plmn-Identity					PLMN-Identity, 
	rat-RestrictionInformation		RAT-RestrictionInformation, 
	iE-Extensions		ProtocolExtensionContainer { {RAT-RestrictionsItem-ExtIEs} } OPTIONAL, 
	...
}

RAT-RestrictionsItem-ExtIEs XNAP-PROTOCOL-EXTENSION ::={
	{ ID id-ExtendedRATRestrictionInformation	CRITICALITY ignore	EXTENSION ExtendedRATRestrictionInformation		PRESENCE optional}, 
	...
}


RAT-RestrictionInformation ::= BIT STRING {e-UTRA (0), nR (1)} (SIZE(8,  ...))


ForbiddenAreaList ::= SEQUENCE (SIZE(1..maxnoofPLMNs)) OF ForbiddenAreaItem


ForbiddenAreaItem ::= SEQUENCE {
	plmn-Identity		PLMN-Identity, 
	forbidden-TACs		SEQUENCE (SIZE(1..maxnoofForbiddenTACs)) OF TAC, 
	iE-Extensions		ProtocolExtensionContainer { {ForbiddenAreaItem-ExtIEs} } OPTIONAL, 
	...
}

ForbiddenAreaItem-ExtIEs XNAP-PROTOCOL-EXTENSION ::={
	...
}


ServiceAreaList ::= SEQUENCE (SIZE(1..maxnoofPLMNs)) OF ServiceAreaItem


ServiceAreaItem ::= SEQUENCE {
	plmn-Identity						PLMN-Identity, 
	allowed-TACs-ServiceArea			SEQUENCE (SIZE(1..maxnoofAllowedAreas)) OF TAC		OPTIONAL, 
	not-allowed-TACs-ServiceArea		SEQUENCE (SIZE(1..maxnoofAllowedAreas)) OF TAC		OPTIONAL, 
	iE-Extensions		ProtocolExtensionContainer { {ServiceAreaItem-ExtIEs} }				OPTIONAL, 
	...
}

ServiceAreaItem-ExtIEs XNAP-PROTOCOL-EXTENSION ::={
	...
}

MR-DC-ResourceCoordinationInfo ::= SEQUENCE {
		ng-RAN-Node-ResourceCoordinationInfo			NG-RAN-Node-ResourceCoordinationInfo, 
		iE-Extension											ProtocolExtensionContainer { {MR-DC-ResourceCoordinationInfo-ExtIEs}}	OPTIONAL, 
		...
} 

MR-DC-ResourceCoordinationInfo-ExtIEs XNAP-PROTOCOL-EXTENSION ::= {
...
}

NG-RAN-Node-ResourceCoordinationInfo ::= CHOICE {
		eutra-resource-coordination-info					E-UTRA-ResourceCoordinationInfo, 
		nr-resource-coordination-info						NR-ResourceCoordinationInfo
}

E-UTRA-ResourceCoordinationInfo ::= SEQUENCE {
		e-utra-cell												E-UTRA-CGI, 
		ul-coordination-info									BIT STRING (SIZE (6..4400)), 
		dl-coordination-info									BIT STRING (SIZE (6..4400))	OPTIONAL, 
		nr-cell													NR-CGI	OPTIONAL, 
		e-utra-coordination-assistance-info				E-UTRA-CoordinationAssistanceInfo	OPTIONAL, 
		iE-Extension			ProtocolExtensionContainer { {E-UTRA-ResourceCoordinationInfo-ExtIEs} } 	OPTIONAL, 
	...
}

E-UTRA-ResourceCoordinationInfo-ExtIEs XNAP-PROTOCOL-EXTENSION ::= {
	...
}

E-UTRA-CoordinationAssistanceInfo ::= ENUMERATED {coordination-not-required,  ...}

NR-ResourceCoordinationInfo ::= SEQUENCE {
		nr-cell													NR-CGI, 
		ul-coordination-info									BIT STRING (SIZE (6..4400)), 
		dl-coordination-info									BIT STRING (SIZE (6..4400))	OPTIONAL, 
		e-utra-cell												E-UTRA-CGI	OPTIONAL, 
		nr-coordination-assistance-info					NR-CoordinationAssistanceInfo		OPTIONAL, 
		iE-Extension			ProtocolExtensionContainer { {NR-ResourceCoordinationInfo-ExtIEs} } 	OPTIONAL, 
	...
}

NR-ResourceCoordinationInfo-ExtIEs XNAP-PROTOCOL-EXTENSION ::= {
	...
}


NR-CoordinationAssistanceInfo ::= ENUMERATED {coordination-not-required,  ...}

MessageOversizeNotification ::= SEQUENCE {
	maximumCellListSize								MaximumCellListSize, 
	iE-Extension				ProtocolExtensionContainer { {MessageOversizeNotification-ExtIEs}}	OPTIONAL, 
	...
}

MessageOversizeNotification-ExtIEs XNAP-PROTOCOL-EXTENSION ::= {
	...
}

MaximumCellListSize ::= INTEGER(1..16384,  ...)


NBIoT-UL-DL-AlignmentOffset ::= ENUMERATED {
	khz-7dot5, 
	khz0, 
	khz7dot5, 
	...
}
NE-DC-TDM-Pattern ::= SEQUENCE {
		subframeAssignment			ENUMERATED {sa0, sa1, sa2, sa3, sa4, sa5, sa6}, 
		harqOffset					INTEGER (0..9), 
		iE-Extension				ProtocolExtensionContainer { {NE-DC-TDM-Pattern-ExtIEs}}	OPTIONAL, 
		...
}

NE-DC-TDM-Pattern-ExtIEs XNAP-PROTOCOL-EXTENSION ::= {
...
}

NeighbourInformation-E-UTRA ::= SEQUENCE (SIZE(1..maxnoofNeighbours)) OF NeighbourInformation-E-UTRA-Item

NeighbourInformation-E-UTRA-Item ::= SEQUENCE {
	e-utra-PCI			E-UTRAPCI, 
	e-utra-cgi			E-UTRA-CGI, 
	earfcn				E-UTRAARFCN, 
	tac					TAC, 
	ranac				RANAC																		OPTIONAL, 
	iE-Extensions		ProtocolExtensionContainer { {NeighbourInformation-E-UTRA-Item-ExtIEs} } 	OPTIONAL, 
	...
}

NeighbourInformation-E-UTRA-Item-ExtIEs XNAP-PROTOCOL-EXTENSION ::={
	...
}


NeighbourInformation-NR ::= SEQUENCE (SIZE(1..maxnoofNeighbours)) OF NeighbourInformation-NR-Item

NeighbourInformation-NR-Item ::= SEQUENCE {
	nr-PCI								NRPCI, 
	nr-cgi								NR-CGI, 
	tac									TAC, 
	ranac								RANAC														OPTIONAL, 
	nr-mode-info						NeighbourInformation-NR-ModeInfo, 
	connectivitySupport					Connectivity-Support, 
	measurementTimingConfiguration		OCTET STRING, 
	iE-Extensions			ProtocolExtensionContainer { {NeighbourInformation-NR-Item-ExtIEs} } 	OPTIONAL, 
	...
}

NeighbourInformation-NR-Item-ExtIEs XNAP-PROTOCOL-EXTENSION ::={
	...
}


NeighbourInformation-NR-ModeInfo ::= CHOICE {
	fdd-info				NeighbourInformation-NR-ModeFDDInfo, 
	tdd-info				NeighbourInformation-NR-ModeTDDInfo, 
	choice-extension		ProtocolIE-Single-Container { {NeighbourInformation-NR-ModeInfo-ExtIEs} }
}

NeighbourInformation-NR-ModeInfo-ExtIEs XNAP-PROTOCOL-IES ::= {
	...
}


NeighbourInformation-NR-ModeFDDInfo ::= SEQUENCE {
	ul-NR-FreqInfo		NRFrequencyInfo, 
	dl-NR-FequInfo		NRFrequencyInfo, 
	ie-Extensions		ProtocolExtensionContainer { {NeighbourInformation-NR-ModeFDDInfo-ExtIEs} } OPTIONAL, 
	...
}

NeighbourInformation-NR-ModeFDDInfo-ExtIEs XNAP-PROTOCOL-EXTENSION ::= {
	...
}


NeighbourInformation-NR-ModeTDDInfo ::= SEQUENCE {
	nr-FreqInfo			NRFrequencyInfo, 
	ie-Extensions		ProtocolExtensionContainer { {NeighbourInformation-NR-ModeTDDInfo-ExtIEs} } OPTIONAL, 
	...
}

NeighbourInformation-NR-ModeTDDInfo-ExtIEs XNAP-PROTOCOL-EXTENSION ::= {
	...
}


NID	::= BIT STRING (SIZE(44))


NRCarrierList ::= SEQUENCE (SIZE(1..maxnoofNRSCSs)) OF NRCarrierItem

NRCarrierItem ::= SEQUENCE {
	carrierSCS					NRSCS, 
	offsetToCarrier				INTEGER (0..2199,  ...), 
	carrierBandwidth			INTEGER (0..maxnoofPhysicalResourceBlocks,  ...), 
	iE-Extension		ProtocolExtensionContainer { {NRCarrierItem-ExtIEs} } 		OPTIONAL, 
	...
}

NRCarrierItem-ExtIEs XNAP-PROTOCOL-EXTENSION ::= {
	...
}

NRCellPRACHConfig ::= OCTET STRING


NG-RAN-Cell-Identity ::= CHOICE {
	nr						NR-Cell-Identity, 
	e-utra					E-UTRA-Cell-Identity, 
	choice-extension		ProtocolIE-Single-Container { {NG-RAN-Cell-Identity-ExtIEs} }
}

NG-RAN-Cell-Identity-ExtIEs XNAP-PROTOCOL-IES ::= {
	...
}


NG-RAN-CellPCI ::= CHOICE {
	nr					NRPCI, 
	e-utra				E-UTRAPCI, 
	choice-extension	ProtocolIE-Single-Container { {NG-RAN-CellPCI-ExtIEs} }
}

NG-RAN-CellPCI-ExtIEs XNAP-PROTOCOL-IES ::= {
	...
}


NG-RANnodeUEXnAPID ::= INTEGER (0.. 4294967295)


NumberofActiveUEs::= INTEGER(0..16777215,  ...)


NoofRRCConnections ::= INTEGER (1..65536, ...)


NonDynamic5QIDescriptor ::= SEQUENCE {
	fiveQI						FiveQI, 
	priorityLevelQoS			PriorityLevelQoS													OPTIONAL, 
	averagingWindow				AveragingWindow														OPTIONAL, 
	maximumDataBurstVolume		MaximumDataBurstVolume 												OPTIONAL, 
	iE-Extension				ProtocolExtensionContainer { {NonDynamic5QIDescriptor-ExtIEs } }	OPTIONAL, 
	...
}

NonDynamic5QIDescriptor-ExtIEs XNAP-PROTOCOL-EXTENSION ::= {
	{ ID id-CNPacketDelayBudgetDownlink		CRITICALITY ignore	EXTENSION ExtendedPacketDelayBudget	PRESENCE optional}|
	{ ID id-CNPacketDelayBudgetUplink		CRITICALITY ignore	EXTENSION ExtendedPacketDelayBudget	PRESENCE optional}, 
	...
}


NRARFCN	::= INTEGER (0.. maxNRARFCN)


NG-eNB-RadioResourceStatus	::= SEQUENCE {
	dL-GBR-PRB-usage							DL-GBR-PRB-usage, 
	uL-GBR-PRB-usage							UL-GBR-PRB-usage, 
	dL-non-GBR-PRB-usage						DL-non-GBR-PRB-usage, 
	uL-non-GBR-PRB-usage						UL-non-GBR-PRB-usage, 
	dL-Total-PRB-usage						DL-Total-PRB-usage, 
	uL-Total-PRB-usage						UL-Total-PRB-usage, 
	iE-Extensions							ProtocolExtensionContainer { { NG-eNB-RadioResourceStatus-ExtIEs} } OPTIONAL, 
	...
}

NG-eNB-RadioResourceStatus-ExtIEs XNAP-PROTOCOL-EXTENSION ::= {
	...
}


TNLCapacityIndicator ::= SEQUENCE {
	dLTNLOfferedCapacity					OfferedCapacity, 
dLTNLAvailableCapacity					AvailableCapacity, 
uLTNLOfferedCapacity					OfferedCapacity, 
	uLTNLAvailableCapacity					AvailableCapacity, 
	iE-Extensions							ProtocolExtensionContainer { { TNLCapacityIndicator-ExtIEs} } OPTIONAL, 
	...
}

TNLCapacityIndicator-ExtIEs XNAP-PROTOCOL-EXTENSION ::= {
	...
}


NPN-Broadcast-Information ::= CHOICE {
	snpn-Information					NPN-Broadcast-Information-SNPN, 
	pni-npn-Information					NPN-Broadcast-Information-PNI-NPN, 
	choice-extension					ProtocolIE-Single-Container { {NPN-Broadcast-Information-ExtIEs} }
}

NPN-Broadcast-Information-ExtIEs XNAP-PROTOCOL-IES ::= {
	...
}

NPN-Broadcast-Information-SNPN ::= SEQUENCE {
	broadcastSNPNID-List		BroadcastSNPNID-List, 
	iE-Extension				ProtocolExtensionContainer { {NPN-Broadcast-Information-SNPN-ExtIEs} }	OPTIONAL, 
	...
}

NPN-Broadcast-Information-SNPN-ExtIEs XNAP-PROTOCOL-EXTENSION ::= {
	...
}
NPN-Broadcast-Information-PNI-NPN ::= SEQUENCE {
	broadcastPNI-NPN-ID-Information		BroadcastPNI-NPN-ID-Information, 
	iE-Extension						ProtocolExtensionContainer { {NPN-Broadcast-Information-PNI-NPN-ExtIEs} }	OPTIONAL, 
	...
}

NPN-Broadcast-Information-PNI-NPN-ExtIEs XNAP-PROTOCOL-EXTENSION ::= {
	...
}

NPNMobilityInformation::= CHOICE {
	snpn-mobility-information			NPNMobilityInformation-SNPN, 
	pni-npn-mobility-information		NPNMobilityInformation-PNI-NPN, 
	choice-extension					ProtocolIE-Single-Container { {NPNMobilityInformation-ExtIEs} }
}

NPNMobilityInformation-ExtIEs XNAP-PROTOCOL-IES ::= {
	...
}

NPNMobilityInformation-SNPN ::= SEQUENCE {
	serving-NID					NID, 
	iE-Extension				ProtocolExtensionContainer { {NPNMobilityInformation-SNPN-ExtIEs} }	OPTIONAL, 
	...
}

NPNMobilityInformation-SNPN-ExtIEs XNAP-PROTOCOL-EXTENSION ::= {
	...
}

NPNMobilityInformation-PNI-NPN ::= SEQUENCE {
	allowedPNI-NPN-ID-List		AllowedPNI-NPN-ID-List, 
	iE-Extension				ProtocolExtensionContainer { {NPNMobilityInformation-PNI-NPN-ExtIEs} }	OPTIONAL, 
	...
}

NPNMobilityInformation-PNI-NPN-ExtIEs XNAP-PROTOCOL-EXTENSION ::= {
	...
}


NPNPagingAssistanceInformation ::= CHOICE {
	pni-npn-Information					NPNPagingAssistanceInformation-PNI-NPN, 
	choice-extension					ProtocolIE-Single-Container { {NPNPagingAssistanceInformation-ExtIEs} }
}

NPNPagingAssistanceInformation-ExtIEs XNAP-PROTOCOL-IES ::= {
	...
}

NPNPagingAssistanceInformation-PNI-NPN ::= SEQUENCE {
	allowedPNI-NPN-ID-List			AllowedPNI-NPN-ID-List, 
	iE-Extension					ProtocolExtensionContainer { {NPNPagingAssistanceInformation-PNI-NPN-ExtIEs} }	OPTIONAL, 
	...
}

NPNPagingAssistanceInformation-PNI-NPN-ExtIEs XNAP-PROTOCOL-EXTENSION ::= {
	...
}


NPN-Support ::= CHOICE {
	sNPN					NPN-Support-SNPN, 
	choice-Extensions		ProtocolIE-Single-Container { {NPN-Support-ExtIEs} }
}

NPN-Support-ExtIEs XNAP-PROTOCOL-IES ::= {
	...
}

NPN-Support-SNPN ::= SEQUENCE {
	nid					NID, 
	ie-Extension		ProtocolExtensionContainer { {NPN-Support-SNPN-ExtIEs} }
}

NPN-Support-SNPN-ExtIEs XNAP-PROTOCOL-EXTENSION ::= {
	...
}

NR-Cell-Identity		::= BIT STRING (SIZE (36))


NG-RAN-Cell-Identity-ListinRANPagingArea ::= SEQUENCE (SIZE (1..maxnoofCellsinRNA)) OF NG-RAN-Cell-Identity


NR-CGI ::= SEQUENCE {
	plmn-id				PLMN-Identity, 
	nr-CI				NR-Cell-Identity, 
	iE-Extension		ProtocolExtensionContainer { {NR-CGI-ExtIEs} } 	OPTIONAL, 
	...
}

NR-CGI-ExtIEs XNAP-PROTOCOL-EXTENSION ::= {
	...
}

NRCyclicPrefix ::= ENUMERATED {normal,  extended,  ...}

NRDL-ULTransmissionPeriodicity ::= ENUMERATED {ms0p5,  ms0p625,  ms1,  ms1p25,  ms2,  ms2p5,  ms3,  ms4,  ms5,  ms10,  ms20,  ms40,  ms60,  ms80,  ms100,  ms120,  ms140,  ms160,  ...}

NRFrequencyBand ::= INTEGER (1..1024,  ...)


NRFrequencyBand-List ::= SEQUENCE (SIZE(1..maxnoofNRCellBands)) OF NRFrequencyBandItem

NRFrequencyBandItem ::= SEQUENCE {
	nr-frequency-band			NRFrequencyBand, 
	supported-SUL-Band-List		SupportedSULBandList											OPTIONAL, 
	iE-Extension				ProtocolExtensionContainer { {NRFrequencyBandItem-ExtIEs} } 	OPTIONAL, 
	...
}

NRFrequencyBandItem-ExtIEs XNAP-PROTOCOL-EXTENSION ::= {
	...
}



NRFrequencyInfo ::= SEQUENCE {
	nrARFCN				NRARFCN, 
	sul-information		SUL-Information												OPTIONAL, 
	frequencyBand-List		NRFrequencyBand-List, 
	iE-Extension		ProtocolExtensionContainer { {NRFrequencyInfo-ExtIEs} }		OPTIONAL, 
	...
}

NRFrequencyInfo-ExtIEs XNAP-PROTOCOL-EXTENSION ::= {
	{ ID id-FrequencyShift7p5khz	CRITICALITY ignore	EXTENSION FrequencyShift7p5khz	PRESENCE optional }, ...
}

NRMobilityHistoryReport ::= OCTET STRING

NRFrequencyInfoforMDT ::= SEQUENCE {
	nrARFCN				NRARFCN, 
	frequencyBand-List		NRFrequencyBand-List, 
	iE-Extension		ProtocolExtensionContainer { {NRFrequencyInfoforMDT-ExtIEs} }		OPTIONAL, 
	...
}

NRFrequencyInfoforMDT-ExtIEs XNAP-PROTOCOL-EXTENSION ::= {
	...
}

NRModeInfo ::= CHOICE {
	fdd							NRModeInfoFDD, 
	tdd							NRModeInfoTDD, 
	choice-extension			ProtocolIE-Single-Container { {NRModeInfo-ExtIEs} }
}

NRModeInfo-ExtIEs XNAP-PROTOCOL-IES ::= {
	...
}

NRModeInfoFDD ::= SEQUENCE {
	ulNRFrequencyInfo			NRFrequencyInfo, 
	dlNRFrequencyInfo			NRFrequencyInfo, 
	ulNRTransmissonBandwidth	NRTransmissionBandwidth, 
	dlNRTransmissonBandwidth	NRTransmissionBandwidth, 
	iE-Extension		ProtocolExtensionContainer { {NRModeInfoFDD-ExtIEs} } 	OPTIONAL, 
	...
}

NRModeInfoFDD-ExtIEs XNAP-PROTOCOL-EXTENSION ::= {
	{ ID id-ULCarrierList			CRITICALITY ignore	EXTENSION NRCarrierList			PRESENCE optional }, 
...
}


NRModeInfoTDD ::= SEQUENCE {
	nrFrequencyInfo			NRFrequencyInfo, 
	nrTransmissonBandwidth	NRTransmissionBandwidth, 
	iE-Extension			ProtocolExtensionContainer { {NRModeInfoTDD-ExtIEs} } 	OPTIONAL, 
	...
}

NRModeInfoTDD-ExtIEs XNAP-PROTOCOL-EXTENSION ::= {
	{ID id-IntendedTDD-DL-ULConfiguration-NR	CRITICALITY ignore	EXTENSION IntendedTDD-DL-ULConfiguration-NR	PRESENCE optional }|
	{ID id-TDDULDLConfigurationCommonNR			CRITICALITY ignore	EXTENSION TDDULDLConfigurationCommonNR			PRESENCE optional }|
	{ ID id-CarrierList				CRITICALITY ignore	EXTENSION NRCarrierList			PRESENCE optional }, 
	...
}


NRNRB ::= ENUMERATED { nrb11,  nrb18,  nrb24,  nrb25,  nrb31,  nrb32,  nrb38,  nrb51,  nrb52,  nrb65,  nrb66,  nrb78,  nrb79,  nrb93,  nrb106,  nrb107,  nrb121,  nrb132,  nrb133,  nrb135,  nrb160,  nrb162,  nrb189,  nrb216,  nrb217,  nrb245,  nrb264,  nrb270,  nrb273,  ...}

NRPCI ::= INTEGER (0..1007,  ...)

NRSCS ::= ENUMERATED { scs15,  scs30,  scs60,  scs120,  ...}


NRTransmissionBandwidth	::= SEQUENCE {
	nRSCS	NRSCS, 
	nRNRB	NRNRB, 
	iE-Extensions				ProtocolExtensionContainer { {NRTransmissionBandwidth-ExtIEs} } OPTIONAL, 
	...
}

NRTransmissionBandwidth-ExtIEs XNAP-PROTOCOL-EXTENSION ::= {
	...
}


NumberOfAntennaPorts-E-UTRA ::= ENUMERATED {an1,  an2,  an4,  ...}

NG-RANTraceID 				::=OCTET STRING (SIZE (8))

NonGBRResources-Offered ::= ENUMERATED {true,  ...}

NRV2XServicesAuthorized ::= SEQUENCE {
	vehicleUE			VehicleUE											OPTIONAL, 
pedestrianUE 		PedestrianUE						OPTIONAL, 
	iE-Extensions		ProtocolExtensionContainer { {NRV2XServicesAuthorized-ExtIEs} }	OPTIONAL, 
	...
}

NRV2XServicesAuthorized-ExtIEs XNAP-PROTOCOL-EXTENSION ::= {
	...
}


NRUESidelinkAggregateMaximumBitRate ::= SEQUENCE {
	uESidelinkAggregateMaximumBitRate		BitRate, 
	iE-Extensions					ProtocolExtensionContainer { {NRUESidelinkAggregateMaximumBitRate-ExtIEs} } OPTIONAL, 
	...
}

NRUESidelinkAggregateMaximumBitRate-ExtIEs XNAP-PROTOCOL-EXTENSION ::= {
	...
}



OfferedCapacity ::= INTEGER (1.. 16777216, ...)

OffsetOfNbiotChannelNumberToEARFCN ::= ENUMERATED {
		minusTen, 
		minusNine, 
		minusEightDotFive, 
		minusEight, 
		minusSeven, 
		minusSix, 
		minusFive, 
		minusFourDotFive, 
		minusFour, 
		minusThree, 
		minusTwo, 
		minusOne, 
		minusZeroDotFive, 
		zero, 
		one, 
		two, 
		three, 
		threeDotFive, 
		four, 
		five, 
		six, 
		seven, 
		sevenDotFive, 
		eight, 
		nine, 
		...
}



PacketDelayBudget ::= INTEGER (0..1023,  ...)


PacketErrorRate ::= SEQUENCE {
	pER-Scalar			PER-Scalar, 
	pER-Exponent		PER-Exponent, 
	iE-Extensions		ProtocolExtensionContainer { {PacketErrorRate-ExtIEs} }	OPTIONAL, 
	...
}

PacketErrorRate-ExtIEs XNAP-PROTOCOL-EXTENSION ::= {
	...
}

PedestrianUE ::= ENUMERATED { 
	authorized, 
	not-authorized, 
	...
}

PER-Scalar ::= INTEGER (0..9,  ...)

PER-Exponent ::= INTEGER (0..9,  ...)


PacketLossRate ::= INTEGER (0..1000,  ...)


PagingDRX	::= ENUMERATED {
	v32, 
	v64, 
	v128, 
	v256, 
	... , 
	v512, 
	v1024
	}


PagingPriority ::= ENUMERATED {
	priolevel1, 
	priolevel2, 
	priolevel3, 
	priolevel4, 
	priolevel5, 
	priolevel6, 
	priolevel7, 
	priolevel8, 
	...
}

PartialListIndicator ::= ENUMERATED {partial,  ...}

PC5QoSParameters ::= SEQUENCE {
	pc5QoSFlowList				PC5QoSFlowList, 
	pc5LinkAggregatedBitRates	BitRate				OPTIONAL, 
	iE-Extensions		ProtocolExtensionContainer { { PC5QoSParameters-ExtIEs} }	OPTIONAL, 
	...
}


PC5QoSParameters-ExtIEs XNAP-PROTOCOL-EXTENSION ::= {
	...
}

PC5QoSFlowList ::= SEQUENCE (SIZE(1..maxnoofPC5QoSFlows)) OF PC5QoSFlowItem

PC5QoSFlowItem::= SEQUENCE {
	pQI							FiveQI, 
	pc5FlowBitRates				PC5FlowBitRates				OPTIONAL, 
	range						Range						OPTIONAL, 
	iE-Extensions		ProtocolExtensionContainer { { PC5QoSFlowItem-ExtIEs} }	OPTIONAL, 
	...
}

PC5QoSFlowItem-ExtIEs XNAP-PROTOCOL-EXTENSION ::= {
	...
}


PC5FlowBitRates ::= SEQUENCE {
	guaranteedFlowBitRate		BitRate, 
	maximumFlowBitRate			BitRate, 
	iE-Extensions		ProtocolExtensionContainer { { PC5FlowBitRates-ExtIEs} }	OPTIONAL, 
	...
}

PC5FlowBitRates-ExtIEs XNAP-PROTOCOL-EXTENSION ::= {
	...
}

PDCPChangeIndication ::= CHOICE {
	from-S-NG-RAN-node				ENUMERATED {s-ng-ran-node-key-update-required,  pdcp-data-recovery-required,  ...}, 
	from-M-NG-RAN-node				ENUMERATED {pdcp-data-recovery-required,  ...}, 
	choice-extension				ProtocolIE-Single-Container { {PDCPChangeIndication-ExtIEs} }
}

PDCPChangeIndication-ExtIEs XNAP-PROTOCOL-IES ::= {
	...
}


PDCPDuplicationConfiguration ::= ENUMERATED {
	configured, 
	de-configured, 
	...
}


PDCPSNLength ::= SEQUENCE {
	ulPDCPSNLength			ENUMERATED {v12bits,  v18bits,  ...}, 
	dlPDCPSNLength			ENUMERATED {v12bits,  v18bits,  ...}, 
	iE-Extension			ProtocolExtensionContainer { {PDCPSNLength-ExtIEs} }		OPTIONAL, 
	...
}

PDCPSNLength-ExtIEs XNAP-PROTOCOL-EXTENSION ::= {
	...
}



PDUSessionAggregateMaximumBitRate ::= SEQUENCE {
	downlink-session-AMBR				BitRate, 
	uplink-session-AMBR					BitRate, 
	iE-Extensions						ProtocolExtensionContainer { {PDUSessionAggregateMaximumBitRate-ExtIEs} }	OPTIONAL, 
	...
}

PDUSessionAggregateMaximumBitRate-ExtIEs XNAP-PROTOCOL-EXTENSION ::= {
	...
}


PDUSession-List ::= SEQUENCE (SIZE (1.. maxnoofPDUSessions)) OF PDUSession-ID


PDUSession-List-withCause ::= SEQUENCE (SIZE (1.. maxnoofPDUSessions)) OF PDUSession-List-withCause-Item

PDUSession-List-withCause-Item ::= SEQUENCE {
	pduSessionId		PDUSession-ID, 
	cause				Cause				OPTIONAL, 
	iE-Extension		ProtocolExtensionContainer { {PDUSession-List-withCause-Item-ExtIEs} }	OPTIONAL, 
	...
}

PDUSession-List-withCause-Item-ExtIEs XNAP-PROTOCOL-EXTENSION ::= {
	...
}


PDUSession-List-withDataForwardingFromTarget ::= SEQUENCE (SIZE (1.. maxnoofPDUSessions)) OF 
															PDUSession-List-withDataForwardingFromTarget-Item

PDUSession-List-withDataForwardingFromTarget-Item ::= SEQUENCE {
	pduSessionId						PDUSession-ID, 
	dataforwardinginfoTarget			DataForwardingInfoFromTargetNGRANnode, 
	iE-Extension		ProtocolExtensionContainer { {PDUSession-List-withDataForwardingFromTarget-Item-ExtIEs} }	OPTIONAL, 
	...
}

PDUSession-List-withDataForwardingFromTarget-Item-ExtIEs XNAP-PROTOCOL-EXTENSION ::= {
	{ ID id-DRB-IDs-takenintouse		CRITICALITY reject	EXTENSION DRB-List	PRESENCE optional}, 
	...
}


PDUSession-List-withDataForwardingRequest ::= SEQUENCE (SIZE (1.. maxnoofPDUSessions)) OF 
															PDUSession-List-withDataForwardingRequest-Item

PDUSession-List-withDataForwardingRequest-Item ::= SEQUENCE {
	pduSessionId							PDUSession-ID, 
	dataforwardingInfofromSource			DataforwardingandOffloadingInfofromSource					OPTIONAL, 
	dRBtoBeReleasedList						DRBToQoSFlowMapping-List									OPTIONAL, 
	iE-Extension		ProtocolExtensionContainer { {PDUSession-List-withDataForwardingRequest-Item-ExtIEs} }	OPTIONAL, 
	...
}

PDUSession-List-withDataForwardingRequest-Item-ExtIEs XNAP-PROTOCOL-EXTENSION ::= {
	...
}












PDUSessionResourcesAdmitted-List ::= SEQUENCE (SIZE(1..maxnoofPDUSessions)) OF PDUSessionResourcesAdmitted-Item

PDUSessionResourcesAdmitted-Item ::= SEQUENCE {
	pduSessionId						PDUSession-ID, 
	pduSessionResourceAdmittedInfo		PDUSessionResourceAdmittedInfo, 
	iE-Extensions						ProtocolExtensionContainer { {PDUSessionResourcesAdmitted-Item-ExtIEs} } 	OPTIONAL, 
	...
}

PDUSessionResourcesAdmitted-Item-ExtIEs XNAP-PROTOCOL-EXTENSION ::= {
	...
}


PDUSessionResourceAdmittedInfo ::= SEQUENCE {
	dL-NG-U-TNL-Information-Unchanged		ENUMERATED {true,  ...}														OPTIONAL, 
	qosFlowsAdmitted-List					QoSFlowsAdmitted-List, 
	qosFlowsNotAdmitted-List				QoSFlows-List-withCause														OPTIONAL, 
	dataForwardingInfoFromTarget			DataForwardingInfoFromTargetNGRANnode										OPTIONAL, 
	iE-Extensions						ProtocolExtensionContainer { {PDUSessionResourceAdmittedInfo-ExtIEs} }	OPTIONAL, 
	...
}

PDUSessionResourceAdmittedInfo-ExtIEs XNAP-PROTOCOL-EXTENSION ::= {
{ ID id-SecondarydataForwardingInfoFromTarget-List	CRITICALITY ignore	EXTENSION SecondarydataForwardingInfoFromTarget-List	PRESENCE optional}, 
	...
}







PDUSessionResourcesNotAdmitted-List ::= SEQUENCE (SIZE (1..maxnoofPDUSessions)) OF PDUSessionResourcesNotAdmitted-Item

PDUSessionResourcesNotAdmitted-Item ::= SEQUENCE {
	pduSessionId				PDUSession-ID, 
	cause						Cause				OPTIONAL, 
	iE-Extension		ProtocolExtensionContainer { {PDUSessionResourcesNotAdmitted-Item-Item-ExtIEs} }	OPTIONAL, 
	...
}

PDUSessionResourcesNotAdmitted-Item-Item-ExtIEs XNAP-PROTOCOL-EXTENSION ::= {
	...
}







PDUSessionResourcesToBeSetup-List ::= SEQUENCE (SIZE(1..maxnoofPDUSessions)) OF PDUSessionResourcesToBeSetup-Item

PDUSessionResourcesToBeSetup-Item ::= SEQUENCE {
	pduSessionId					PDUSession-ID, 
	s-NSSAI							S-NSSAI, 
	pduSessionAMBR					PDUSessionAggregateMaximumBitRate													OPTIONAL, 
	uL-NG-U-TNLatUPF				UPTransportLayerInformation, 
	source-DL-NG-U-TNL-Information  UPTransportLayerInformation															OPTIONAL, 
	securityIndication				SecurityIndication																	OPTIONAL, 
	pduSessionType					PDUSessionType, 
	pduSessionNetworkInstance		PDUSessionNetworkInstance															OPTIONAL, 
	qosFlowsToBeSetup-List			QoSFlowsToBeSetup-List, 
	dataforwardinginfofromSource	DataforwardingandOffloadingInfofromSource											OPTIONAL, 
	iE-Extensions					ProtocolExtensionContainer { {PDUSessionResourcesToBeSetup-Item-ExtIEs} } 	OPTIONAL, 
	...
}

PDUSessionResourcesToBeSetup-Item-ExtIEs XNAP-PROTOCOL-EXTENSION ::= {
{ ID id-Additional-UL-NG-U-TNLatUPF-List	CRITICALITY ignore	EXTENSION Additional-UL-NG-U-TNLatUPF-List 	PRESENCE optional}|
{ ID id-PDUSessionCommonNetworkInstance		CRITICALITY ignore	EXTENSION PDUSessionCommonNetworkInstance		PRESENCE optional}|
{ ID id-Redundant-UL-NG-U-TNLatUPF			CRITICALITY	ignore	EXTENSION UPTransportLayerInformation		PRESENCE optional}|
{ ID id-Additional-Redundant-UL-NG-U-TNLatUPF-List	CRITICALITY ignore	EXTENSION Additional-UL-NG-U-TNLatUPF-List  PRESENCE optional}|
{ ID id-RedundantCommonNetworkInstance		CRITICALITY ignore	EXTENSION PDUSessionCommonNetworkInstance	PRESENCE optional}|
{ ID id-RedundantPDUSessionInformation		CRITICALITY ignore	EXTENSION RedundantPDUSessionInformation	PRESENCE optional}, 
	...
}







PDUSessionResourceSetupInfo-SNterminated ::= SEQUENCE {
	uL-NG-U-TNLatUPF				UPTransportLayerInformation, 
	pduSessionType					PDUSessionType, 
	pduSessionNetworkInstance		PDUSessionNetworkInstance																	OPTIONAL, 
	qosFlowsToBeSetup-List			QoSFlowsToBeSetup-List-Setup-SNterminated, 
	dataforwardinginfofromSource	DataforwardingandOffloadingInfofromSource													OPTIONAL, 
	securityIndication				SecurityIndication																			OPTIONAL, 
	iE-Extensions					ProtocolExtensionContainer { {PDUSessionResourceSetupInfo-SNterminated-ExtIEs} }	OPTIONAL, 
	...
}

PDUSessionResourceSetupInfo-SNterminated-ExtIEs XNAP-PROTOCOL-EXTENSION ::= {
	{ ID id-SecurityResult						CRITICALITY reject	EXTENSION SecurityResult							PRESENCE optional}|
	{ ID id-PDUSessionCommonNetworkInstance		CRITICALITY ignore	EXTENSION PDUSessionCommonNetworkInstance		PRESENCE optional}|
	{ID id-DefaultDRB-Allowed					CRITICALITY ignore	EXTENSION DefaultDRB-Allowed						PRESENCE optional}|
	{ ID id-SplitSessionIndicator				CRITICALITY reject	EXTENSION SplitSessionIndicator					PRESENCE optional}|
	{ID id-NonGBRResources-Offered				CRITICALITY ignore	EXTENSION NonGBRResources-Offered				PRESENCE optional}|
	{ ID id-Redundant-UL-NG-U-TNLatUPF			CRITICALITY	ignore	EXTENSION UPTransportLayerInformation			PRESENCE optional}|
	{ ID id-RedundantCommonNetworkInstance		CRITICALITY ignore	EXTENSION PDUSessionCommonNetworkInstance		PRESENCE optional}|
	{ ID id-RedundantPDUSessionInformation		CRITICALITY ignore	EXTENSION RedundantPDUSessionInformation		PRESENCE optional}, 
	...
}

QoSFlowsToBeSetup-List-Setup-SNterminated ::= SEQUENCE (SIZE(1..maxnoofQoSFlows)) OF QoSFlowsToBeSetup-List-Setup-SNterminated-Item

QoSFlowsToBeSetup-List-Setup-SNterminated-Item ::= SEQUENCE {
	qfi								QoSFlowIdentifier, 
	qosFlowLevelQoSParameters		QoSFlowLevelQoSParameters, 
	offeredGBRQoSFlowInfo			GBRQoSFlowInfo																						OPTIONAL, 
	iE-Extensions					ProtocolExtensionContainer { {QoSFlowsToBeSetup-List-Setup-SNterminated-Item-ExtIEs} }	OPTIONAL, 
	...
}

QoSFlowsToBeSetup-List-Setup-SNterminated-Item-ExtIEs XNAP-PROTOCOL-EXTENSION ::= {
	{ ID id-TSCTrafficCharacteristics		CRITICALITY ignore	EXTENSION TSCTrafficCharacteristics 	PRESENCE optional}|
	{ ID id-RedundantQoSFlowIndicator		CRITICALITY ignore	EXTENSION RedundantQoSFlowIndicator	PRESENCE optional}, 
	...
}







PDUSessionResourceSetupResponseInfo-SNterminated ::= SEQUENCE {
	dL-NG-U-TNLatNG-RAN				UPTransportLayerInformation, 
	dRBsToBeSetup					DRBsToBeSetupList-SetupResponse-SNterminated 	OPTIONAL, 
	dataforwardinginfoTarget		DataForwardingInfoFromTargetNGRANnode			OPTIONAL, 
	qosFlowsNotAdmittedList			QoSFlows-List-withCause							OPTIONAL, 
	securityResult					SecurityResult									OPTIONAL, 
	iE-Extensions					ProtocolExtensionContainer { {PDUSessionResourceSetupResponseInfo-SNterminated-ExtIEs} } 	OPTIONAL, 
	...
}

PDUSessionResourceSetupResponseInfo-SNterminated-ExtIEs XNAP-PROTOCOL-EXTENSION ::= {
	{ ID id-Redundant-DL-NG-U-TNLatNG-RAN				CRITICALITY ignore	EXTENSION UPTransportLayerInformation	PRESENCE optional}|
	{ ID id-UsedRSNInformation							CRITICALITY ignore	EXTENSION RedundantPDUSessionInformation	PRESENCE optional}, 
	...
}

DRBsToBeSetupList-SetupResponse-SNterminated ::= SEQUENCE (SIZE(1..maxnoofDRBs)) OF DRBsToBeSetupList-SetupResponse-SNterminated-Item

DRBsToBeSetupList-SetupResponse-SNterminated-Item ::= SEQUENCE {
	drb-ID													DRB-ID, 
	sN-UL-PDCP-UP-TNLInfo									UPTransportParameters, 
	dRB-QoS													QoSFlowLevelQoSParameters, 
	pDCP-SNLength											PDCPSNLength						OPTIONAL, 
	rLC-Mode												RLCMode, 
		uL-Configuration									ULConfiguration						OPTIONAL, 
	secondary-SN-UL-PDCP-UP-TNLInfo							UPTransportParameters				OPTIONAL, 
	duplicationActivation									DuplicationActivation				OPTIONAL, 
	qoSFlowsMappedtoDRB-SetupResponse-SNterminated			QoSFlowsMappedtoDRB-SetupResponse-SNterminated, 
	iE-Extensions					ProtocolExtensionContainer { {DRBsToBeSetupList-SetupResponse-SNterminated-Item-ExtIEs} } 	OPTIONAL, 
	...
}

DRBsToBeSetupList-SetupResponse-SNterminated-Item-ExtIEs XNAP-PROTOCOL-EXTENSION ::= {
	{ ID id-Additional-PDCP-Duplication-TNL-List		CRITICALITY ignore	EXTENSION Additional-PDCP-Duplication-TNL-List	PRESENCE optional}|
	{ ID id-RLCDuplicationInformation					CRITICALITY ignore	EXTENSION RLCDuplicationInformation	PRESENCE optional}, 
	...
}

QoSFlowsMappedtoDRB-SetupResponse-SNterminated ::= SEQUENCE (SIZE(1..maxnoofQoSFlows)) OF
																		QoSFlowsMappedtoDRB-SetupResponse-SNterminated-Item

QoSFlowsMappedtoDRB-SetupResponse-SNterminated-Item ::= SEQUENCE {
	qoSFlowIdentifier				QoSFlowIdentifier, 
	mCGRequestedGBRQoSFlowInfo		GBRQoSFlowInfo														OPTIONAL, 
	qosFlowMappingIndication		QoSFlowMappingIndication											OPTIONAL, 
	iE-Extensions		ProtocolExtensionContainer { {QoSFlowsMappedtoDRB-SetupResponse-SNterminated-Item-ExtIEs} } 	OPTIONAL, 
	...
}

QoSFlowsMappedtoDRB-SetupResponse-SNterminated-Item-ExtIEs XNAP-PROTOCOL-EXTENSION ::= {
	...
}







PDUSessionResourceSetupInfo-MNterminated ::= SEQUENCE {
	pduSessionType					PDUSessionType, 
	dRBsToBeSetup					DRBsToBeSetupList-Setup-MNterminated, 
	iE-Extensions					ProtocolExtensionContainer { {PDUSessionResourceSetupInfo-MNterminated-ExtIEs} } 	OPTIONAL, 
	...
}

PDUSessionResourceSetupInfo-MNterminated-ExtIEs XNAP-PROTOCOL-EXTENSION ::= {
	...
}

DRBsToBeSetupList-Setup-MNterminated ::= SEQUENCE (SIZE(1..maxnoofDRBs)) OF DRBsToBeSetupList-Setup-MNterminated-Item

DRBsToBeSetupList-Setup-MNterminated-Item ::= SEQUENCE {
	drb-ID													DRB-ID, 
	mN-UL-PDCP-UP-TNLInfo									UPTransportParameters, 
	rLC-Mode												RLCMode, 
	uL-Configuration										ULConfiguration						OPTIONAL, 
	dRB-QoS													QoSFlowLevelQoSParameters, 
	pDCP-SNLength											PDCPSNLength						OPTIONAL, 
	secondary-MN-UL-PDCP-UP-TNLInfo							UPTransportParameters				OPTIONAL, 
	duplicationActivation									DuplicationActivation				OPTIONAL, 
	qoSFlowsMappedtoDRB-Setup-MNterminated		QoSFlowsMappedtoDRB-Setup-MNterminated, 
	iE-Extensions					ProtocolExtensionContainer { {DRBsToBeSetupList-Setup-MNterminated-Item-ExtIEs} } 	OPTIONAL, 
	...
}

DRBsToBeSetupList-Setup-MNterminated-Item-ExtIEs XNAP-PROTOCOL-EXTENSION ::= {
	{ ID id-Additional-PDCP-Duplication-TNL-List		CRITICALITY ignore	EXTENSION Additional-PDCP-Duplication-TNL-List	PRESENCE optional}|
	{ ID id-RLCDuplicationInformation					CRITICALITY ignore	EXTENSION RLCDuplicationInformation	PRESENCE optional}, 
	...
}

QoSFlowsMappedtoDRB-Setup-MNterminated ::= SEQUENCE (SIZE(1..maxnoofQoSFlows)) OF QoSFlowsMappedtoDRB-Setup-MNterminated-Item

QoSFlowsMappedtoDRB-Setup-MNterminated-Item ::= SEQUENCE {
	qoSFlowIdentifier				QoSFlowIdentifier, 
	qoSFlowLevelQoSParameters		QoSFlowLevelQoSParameters, 
	qosFlowMappingIndication		QoSFlowMappingIndication		OPTIONAL, 
	iE-Extensions		ProtocolExtensionContainer { {QoSFlowsMappedtoDRB-Setup-MNterminated-Item-ExtIEs} } 	OPTIONAL, 
	...
}

QoSFlowsMappedtoDRB-Setup-MNterminated-Item-ExtIEs XNAP-PROTOCOL-EXTENSION ::= {
	{ ID id-TSCTrafficCharacteristics		CRITICALITY ignore	EXTENSION TSCTrafficCharacteristics 	PRESENCE optional}, 
	...
}







PDUSessionResourceSetupResponseInfo-MNterminated ::= SEQUENCE {
	dRBsAdmittedList				DRBsAdmittedList-SetupResponse-MNterminated, 
	iE-Extensions					ProtocolExtensionContainer { {PDUSessionResourceSetupResponseInfo-MNterminated-ExtIEs} } 	OPTIONAL, 
	...
}

PDUSessionResourceSetupResponseInfo-MNterminated-ExtIEs XNAP-PROTOCOL-EXTENSION ::= {
	{ID id-DRBsNotAdmittedSetupModifyList	CRITICALITY ignore	EXTENSION DRB-List-withCause		PRESENCE optional}, 
	...
}

DRBsAdmittedList-SetupResponse-MNterminated ::= SEQUENCE (SIZE(1..maxnoofDRBs)) OF DRBsAdmittedList-SetupResponse-MNterminated-Item

DRBsAdmittedList-SetupResponse-MNterminated-Item ::= SEQUENCE {
	drb-ID									DRB-ID, 
	sN-DL-SCG-UP-TNLInfo					UPTransportParameters, 
	secondary-SN-DL-SCG-UP-TNLInfo			UPTransportParameters				OPTIONAL, 
	lCID									LCID								OPTIONAL, 
	iE-Extensions					ProtocolExtensionContainer { {DRBsAdmittedList-SetupResponse-MNterminated-Item-ExtIEs} } 	OPTIONAL, 
	...
}

DRBsAdmittedList-SetupResponse-MNterminated-Item-ExtIEs XNAP-PROTOCOL-EXTENSION ::= {
	{ ID id-Additional-PDCP-Duplication-TNL-List		CRITICALITY ignore	EXTENSION Additional-PDCP-Duplication-TNL-List	PRESENCE optional}, 
	...
}







PDUSessionResourceModificationInfo-SNterminated ::= SEQUENCE {
	uL-NG-U-TNLatUPF				UPTransportLayerInformation						OPTIONAL, 
	pduSessionNetworkInstance		PDUSessionNetworkInstance						OPTIONAL, 
	qosFlowsToBeSetup-List			QoSFlowsToBeSetup-List-Setup-SNterminated		OPTIONAL, 
	dataforwardinginfofromSource	DataforwardingandOffloadingInfofromSource		OPTIONAL, 
	qosFlowsToBeModified-List		QoSFlowsToBeSetup-List-Modified-SNterminated	OPTIONAL, 
	qoSFlowsToBeReleased-List		QoSFlows-List-withCause							OPTIONAL, 
	drbsToBeModifiedList			DRBsToBeModified-List-Modified-SNterminated		OPTIONAL, 
	dRBsToBeReleased				DRB-List-withCause								OPTIONAL, 
	iE-Extensions					ProtocolExtensionContainer { {PDUSessionResourceModificationInfo-SNterminated-ExtIEs} } 	OPTIONAL, 
	...
}

PDUSessionResourceModificationInfo-SNterminated-ExtIEs XNAP-PROTOCOL-EXTENSION ::= {
	{ ID id-PDUSessionCommonNetworkInstance		CRITICALITY ignore	EXTENSION PDUSessionCommonNetworkInstance		PRESENCE optional}|
	{ID id-DefaultDRB-Allowed					CRITICALITY ignore	EXTENSION DefaultDRB-Allowed						PRESENCE optional}|
	{ID id-NonGBRResources-Offered				CRITICALITY ignore	EXTENSION NonGBRResources-Offered				PRESENCE optional}|
	{ID id-Redundant-UL-NG-U-TNLatUPF			CRITICALITY ignore	EXTENSION UPTransportLayerInformation	PRESENCE optional}|
	{ID id-RedundantCommonNetworkInstance		CRITICALITY ignore	EXTENSION PDUSessionCommonNetworkInstance	PRESENCE optional}, 
	...
}

QoSFlowsToBeSetup-List-Modified-SNterminated ::= SEQUENCE (SIZE(1..maxnoofQoSFlows)) OF QoSFlowsToBeSetup-List-Modified-SNterminated-Item

QoSFlowsToBeSetup-List-Modified-SNterminated-Item ::= SEQUENCE {
	qfi								QoSFlowIdentifier, 
	qosFlowLevelQoSParameters		QoSFlowLevelQoSParameters							OPTIONAL, 
	offeredGBRQoSFlowInfo			GBRQoSFlowInfo										OPTIONAL, 
	qosFlowMappingIndication		QoSFlowMappingIndication 							OPTIONAL, 
	iE-Extensions					ProtocolExtensionContainer { {QoSFlowsToBeSetup-List-Modified-SNterminated-Item-ExtIEs} } 	OPTIONAL, 
	...
}

QoSFlowsToBeSetup-List-Modified-SNterminated-Item-ExtIEs XNAP-PROTOCOL-EXTENSION ::= {
	{ ID id-TSCTrafficCharacteristics		CRITICALITY ignore	EXTENSION TSCTrafficCharacteristics 	PRESENCE optional}|
	{ ID id-RedundantQoSFlowIndicator		CRITICALITY ignore	EXTENSION RedundantQoSFlowIndicator	PRESENCE optional}, 
	...
}

DRBsToBeModified-List-Modified-SNterminated ::= SEQUENCE (SIZE(1..maxnoofDRBs)) OF DRBsToBeModified-List-Modified-SNterminated-Item

DRBsToBeModified-List-Modified-SNterminated-Item ::= SEQUENCE {
	drb-ID									DRB-ID, 
	mN-DL-SCG-UP-TNLInfo					UPTransportParameters		OPTIONAL, 
	secondary-MN-DL-SCG-UP-TNLInfo			UPTransportParameters		OPTIONAL, 
	lCID									LCID						OPTIONAL, 
	rlc-status								RLC-Status					OPTIONAL, 
	iE-Extensions					ProtocolExtensionContainer { {DRBsToBeModified-List-Modified-SNterminated-Item-ExtIEs} } 	OPTIONAL, 
	...
}

DRBsToBeModified-List-Modified-SNterminated-Item-ExtIEs XNAP-PROTOCOL-EXTENSION ::= {
	{ ID id-Additional-PDCP-Duplication-TNL-List		CRITICALITY ignore	EXTENSION Additional-PDCP-Duplication-TNL-List	PRESENCE optional}, 
	...
}







PDUSessionResourceModificationResponseInfo-SNterminated ::= SEQUENCE {
	dL-NG-U-TNLatNG-RAN				UPTransportLayerInformation								OPTIONAL, 
	dRBsToBeSetup					DRBsToBeSetupList-SetupResponse-SNterminated			OPTIONAL, 
	dataforwardinginfoTarget		DataForwardingInfoFromTargetNGRANnode					OPTIONAL, 
	dRBsToBeModified				DRBsToBeModifiedList-ModificationResponse-SNterminated	OPTIONAL, 
	dRBsToBeReleased				DRB-List-withCause										OPTIONAL, 
	dataforwardinginfofromSource	DataforwardingandOffloadingInfofromSource				OPTIONAL, 
	qosFlowsNotAdmittedTBAdded		QoSFlows-List-withCause									OPTIONAL, 
	qosFlowsReleased				QoSFlows-List-withCause									OPTIONAL, 
	iE-Extensions					ProtocolExtensionContainer { {PDUSessionResourceModificationResponseInfo-SNterminated-ExtIEs} } 	OPTIONAL, 
	...
}

PDUSessionResourceModificationResponseInfo-SNterminated-ExtIEs XNAP-PROTOCOL-EXTENSION ::= {
	{ ID id-DRB-IDs-takenintouse		CRITICALITY reject	EXTENSION DRB-List	PRESENCE optional}|
	{ ID id-Redundant-DL-NG-U-TNLatNG-RAN	CRITICALITY ignore	EXTENSION UPTransportLayerInformation	PRESENCE optional}, 
	...
}

DRBsToBeModifiedList-ModificationResponse-SNterminated ::= SEQUENCE (SIZE(1..maxnoofDRBs)) OF 
																				DRBsToBeModifiedList-ModificationResponse-SNterminated-Item

DRBsToBeModifiedList-ModificationResponse-SNterminated-Item ::= SEQUENCE {
	drb-ID													DRB-ID, 
	sN-UL-PDCP-UP-TNLInfo									UPTransportParameters									OPTIONAL, 
	dRB-QoS													QoSFlowLevelQoSParameters								OPTIONAL, 
	qoSFlowsMappedtoDRB-SetupResponse-SNterminated			QoSFlowsMappedtoDRB-SetupResponse-SNterminated		OPTIONAL, 
	iE-Extensions		ProtocolExtensionContainer { {DRBsToBeModifiedList-ModificationResponse-SNterminated-Item-ExtIEs} } 	OPTIONAL, 
	...
}

DRBsToBeModifiedList-ModificationResponse-SNterminated-Item-ExtIEs XNAP-PROTOCOL-EXTENSION ::= {
	{ ID id-Additional-PDCP-Duplication-TNL-List		CRITICALITY ignore	EXTENSION Additional-PDCP-Duplication-TNL-List	PRESENCE optional}|
	{ ID id-RLCDuplicationInformation					CRITICALITY ignore	EXTENSION RLCDuplicationInformation	PRESENCE optional}, 
	...
}







PDUSessionResourceModificationInfo-MNterminated ::= SEQUENCE {
	pduSessionType					PDUSessionType, 
	dRBsToBeSetup					DRBsToBeSetupList-Setup-MNterminated						OPTIONAL, 
	dRBsToBeModified				DRBsToBeModifiedList-Modification-MNterminated				OPTIONAL, 
	dRBsToBeReleased				DRB-List-withCause											OPTIONAL, 
	iE-Extensions					ProtocolExtensionContainer { {PDUSessionResourceModificationInfo-MNterminated-ExtIEs} } 	OPTIONAL, 
	...
}

PDUSessionResourceModificationInfo-MNterminated-ExtIEs XNAP-PROTOCOL-EXTENSION ::= {
	...
}

DRBsToBeModifiedList-Modification-MNterminated ::= SEQUENCE (SIZE(1..maxnoofDRBs)) OF
																					DRBsToBeModifiedList-Modification-MNterminated-Item

DRBsToBeModifiedList-Modification-MNterminated-Item ::= SEQUENCE {
	drb-ID													DRB-ID, 
	mN-UL-PDCP-UP-TNLInfo									UPTransportParameters						OPTIONAL, 
	dRB-QoS													QoSFlowLevelQoSParameters					OPTIONAL, 
	secondary-MN-UL-PDCP-UP-TNLInfo							UPTransportParameters						OPTIONAL, 
	uL-Configuration										ULConfiguration								OPTIONAL, 
	pdcpDuplicationConfiguration							PDCPDuplicationConfiguration 				OPTIONAL, 
	duplicationActivation									DuplicationActivation						OPTIONAL, 
	qoSFlowsMappedtoDRB-Setup-MNterminated					QoSFlowsMappedtoDRB-Setup-MNterminated	OPTIONAL, 
	iE-Extensions					ProtocolExtensionContainer { {DRBsToBeModifiedList-Modification-MNterminated-Item-ExtIEs} } 	OPTIONAL, 
	...
}

DRBsToBeModifiedList-Modification-MNterminated-Item-ExtIEs XNAP-PROTOCOL-EXTENSION ::= {
	{ ID id-Additional-PDCP-Duplication-TNL-List		CRITICALITY ignore	EXTENSION Additional-PDCP-Duplication-TNL-List	PRESENCE optional}|
	{ ID id-RLCDuplicationInformation					CRITICALITY ignore	EXTENSION RLCDuplicationInformation	PRESENCE optional}, 
	...
}







PDUSessionResourceModificationResponseInfo-MNterminated ::= SEQUENCE {
	dRBsAdmittedList						DRBsAdmittedList-ModificationResponse-MNterminated, 
	dRBsReleasedList						DRB-List																		OPTIONAL, 
	dRBsNotAdmittedSetupModifyList			DRB-List-withCause																OPTIONAL, 
	iE-Extensions					ProtocolExtensionContainer { {PDUSessionResourceModificationResponseInfo-MNterminated-ExtIEs} } 	OPTIONAL, 
	...
}

PDUSessionResourceModificationResponseInfo-MNterminated-ExtIEs XNAP-PROTOCOL-EXTENSION ::= {
	...
}

DRBsAdmittedList-ModificationResponse-MNterminated ::= SEQUENCE (SIZE(1..maxnoofDRBs)) OF DRBsAdmittedList-ModificationResponse-MNterminated-Item

DRBsAdmittedList-ModificationResponse-MNterminated-Item ::= SEQUENCE {
	drb-ID									DRB-ID, 
	sN-DL-SCG-UP-TNLInfo					UPTransportParameters				OPTIONAL, 
	secondary-SN-DL-SCG-UP-TNLInfo			UPTransportParameters				OPTIONAL, 
	lCID									LCID								OPTIONAL, 
	iE-Extensions					ProtocolExtensionContainer { {DRBsAdmittedList-ModificationResponse-MNterminated-Item-ExtIEs} } 	OPTIONAL, 
	...
}

DRBsAdmittedList-ModificationResponse-MNterminated-Item-ExtIEs XNAP-PROTOCOL-EXTENSION ::= {
	{ ID id-Additional-PDCP-Duplication-TNL-List		CRITICALITY ignore	EXTENSION Additional-PDCP-Duplication-TNL-List	PRESENCE optional}, 
	...
}







PDUSessionResourceChangeRequiredInfo-SNterminated ::= SEQUENCE {
	dataforwardinginfofromSource	DataforwardingandOffloadingInfofromSource											OPTIONAL, 
	iE-Extensions					ProtocolExtensionContainer { {PDUSessionResourceChangeRequiredInfo-SNterminated-ExtIEs} } 	OPTIONAL, 
	...
}

PDUSessionResourceChangeRequiredInfo-SNterminated-ExtIEs XNAP-PROTOCOL-EXTENSION ::= {
	...
}







PDUSessionResourceChangeConfirmInfo-SNterminated ::= SEQUENCE {
	dataforwardinginfoTarget		DataForwardingInfoFromTargetNGRANnode				OPTIONAL, 
	iE-Extensions					ProtocolExtensionContainer { {PDUSessionResourceChangeConfirmInfo-SNterminated-ExtIEs} } 	OPTIONAL, 
	...
}

PDUSessionResourceChangeConfirmInfo-SNterminated-ExtIEs XNAP-PROTOCOL-EXTENSION ::= {
	{ ID id-DRB-IDs-takenintouse	CRITICALITY reject	EXTENSION DRB-List	PRESENCE optional}, 
	...
}







PDUSessionResourceChangeRequiredInfo-MNterminated ::= SEQUENCE {
	iE-Extensions					ProtocolExtensionContainer { {PDUSessionResourceChangeRequiredInfo-MNterminated-ExtIEs} } 	OPTIONAL, 
	...
}

PDUSessionResourceChangeRequiredInfo-MNterminated-ExtIEs XNAP-PROTOCOL-EXTENSION ::= {
	...
}







PDUSessionResourceChangeConfirmInfo-MNterminated ::= SEQUENCE {
	iE-Extensions					ProtocolExtensionContainer { {PDUSessionResourceChangeConfirmInfo-MNterminated-ExtIEs} } 	OPTIONAL, 
	...
}

PDUSessionResourceChangeConfirmInfo-MNterminated-ExtIEs XNAP-PROTOCOL-EXTENSION ::= {
	...
}







PDUSessionResourceModRqdInfo-SNterminated ::= SEQUENCE {
	dL-NG-U-TNLatNG-RAN				UPTransportLayerInformation						OPTIONAL, 
	qoSFlowsToBeReleased-List		QoSFlows-List-withCause							OPTIONAL, 
	dataforwardinginfofromSource	DataforwardingandOffloadingInfofromSource		OPTIONAL, 
	drbsToBeSetupList				DRBsToBeSetup-List-ModRqd-SNterminated			OPTIONAL, 
	drbsToBeModifiedList			DRBsToBeModified-List-ModRqd-SNterminated		OPTIONAL, 
	dRBsToBeReleased				DRB-List-withCause								OPTIONAL, 
	iE-Extensions					ProtocolExtensionContainer { {PDUSessionResourceModRqdInfo-SNterminated-ExtIEs} } 	OPTIONAL, 
	...
}

PDUSessionResourceModRqdInfo-SNterminated-ExtIEs XNAP-PROTOCOL-EXTENSION ::= {
	...
}

DRBsToBeSetup-List-ModRqd-SNterminated ::= SEQUENCE (SIZE(1..maxnoofDRBs)) OF DRBsToBeSetup-List-ModRqd-SNterminated-Item

DRBsToBeSetup-List-ModRqd-SNterminated-Item ::= SEQUENCE {
	drb-ID											DRB-ID, 
	pDCP-SNLength									PDCPSNLength											OPTIONAL, 
	sn-UL-PDCP-UPTNLinfo							UPTransportParameters, 
	dRB-QoS											QoSFlowLevelQoSParameters, 
	secondary-SN-UL-PDCP-UP-TNLInfo					UPTransportParameters								OPTIONAL, 
	duplicationActivation							DuplicationActivation								OPTIONAL, 
	uL-Configuration								ULConfiguration										OPTIONAL, 
	qoSFlowsMappedtoDRB-ModRqd-SNterminated			QoSFlowsSetupMappedtoDRB-ModRqd-SNterminated, 
	rLC-Mode										RLCMode, 
	iE-Extensions					ProtocolExtensionContainer { {DRBsToBeSetup-List-ModRqd-SNterminated-Item-ExtIEs} } 	OPTIONAL, 
	...
}

DRBsToBeSetup-List-ModRqd-SNterminated-Item-ExtIEs XNAP-PROTOCOL-EXTENSION ::= {
	{ ID id-Additional-PDCP-Duplication-TNL-List		CRITICALITY ignore	EXTENSION Additional-PDCP-Duplication-TNL-List	PRESENCE optional}, 
	...
}

QoSFlowsSetupMappedtoDRB-ModRqd-SNterminated ::= SEQUENCE (SIZE(1..maxnoofQoSFlows)) OF
																		QoSFlowsSetupMappedtoDRB-ModRqd-SNterminated-Item

QoSFlowsSetupMappedtoDRB-ModRqd-SNterminated-Item ::= SEQUENCE {
	qoSFlowIdentifier				QoSFlowIdentifier, 
	mCGRequestedGBRQoSFlowInfo		GBRQoSFlowInfo														OPTIONAL, 
	iE-Extensions		ProtocolExtensionContainer { {QoSFlowsSetupMappedtoDRB-ModRqd-SNterminated-Item-ExtIEs} } 	OPTIONAL, 
	...
}

QoSFlowsSetupMappedtoDRB-ModRqd-SNterminated-Item-ExtIEs XNAP-PROTOCOL-EXTENSION ::= {
	...
}

DRBsToBeModified-List-ModRqd-SNterminated ::= SEQUENCE (SIZE(1..maxnoofDRBs)) OF DRBsToBeModified-List-ModRqd-SNterminated-Item

DRBsToBeModified-List-ModRqd-SNterminated-Item ::= SEQUENCE {
	drb-ID											DRB-ID, 
	sN-UL-PDCP-UP-TNLInfo							UPTransportParameters									OPTIONAL, 
	dRB-QoS											QoSFlowLevelQoSParameters								OPTIONAL, 
	secondary-SN-UL-PDCP-UP-TNLInfo					UPTransportParameters									OPTIONAL, 
	uL-Configuration								ULConfiguration											OPTIONAL, 
	pdcpDuplicationConfiguration					PDCPDuplicationConfiguration							OPTIONAL, 
	duplicationActivation							DuplicationActivation									OPTIONAL, 
	qoSFlowsMappedtoDRB-ModRqd-SNterminated		QoSFlowsModifiedMappedtoDRB-ModRqd-SNterminated				OPTIONAL, 
	iE-Extensions					ProtocolExtensionContainer { {DRBsToBeModified-List-ModRqd-SNterminated-Item-ExtIEs} } 	OPTIONAL, 
	...
}

DRBsToBeModified-List-ModRqd-SNterminated-Item-ExtIEs XNAP-PROTOCOL-EXTENSION ::= {
	{ ID id-Additional-PDCP-Duplication-TNL-List		CRITICALITY ignore	EXTENSION Additional-PDCP-Duplication-TNL-List	PRESENCE optional}, 
	...
}

QoSFlowsModifiedMappedtoDRB-ModRqd-SNterminated ::= SEQUENCE (SIZE(1..maxnoofQoSFlows)) OF
																		QoSFlowsModifiedMappedtoDRB-ModRqd-SNterminated-Item

QoSFlowsModifiedMappedtoDRB-ModRqd-SNterminated-Item ::= SEQUENCE {
	qoSFlowIdentifier					QoSFlowIdentifier, 
	mCGRequestedGBRQoSFlowInfo			GBRQoSFlowInfo														OPTIONAL, 
	iE-Extensions		ProtocolExtensionContainer { {QoSFlowsModifiedMappedtoDRB-ModRqd-SNterminated-Item-ExtIEs} } 	OPTIONAL, 
	...
}

QoSFlowsModifiedMappedtoDRB-ModRqd-SNterminated-Item-ExtIEs XNAP-PROTOCOL-EXTENSION ::= {
	...
}







PDUSessionResourceModConfirmInfo-SNterminated ::= SEQUENCE {
	uL-NG-U-TNLatUPF						UPTransportLayerInformation								OPTIONAL, 
	dRBsAdmittedList						DRBsAdmittedList-ModConfirm-SNterminated, 
	dRBsNotAdmittedSetupModifyList			DRB-List-withCause										OPTIONAL, 
	dataforwardinginfoTarget				DataForwardingInfoFromTargetNGRANnode					OPTIONAL, 
	iE-Extensions					ProtocolExtensionContainer { {PDUSessionResourceModConfirmInfo-SNterminated-ExtIEs} } 	OPTIONAL, 
	...
}

PDUSessionResourceModConfirmInfo-SNterminated-ExtIEs XNAP-PROTOCOL-EXTENSION ::= {
	{ ID id-DRB-IDs-takenintouse		CRITICALITY reject	EXTENSION DRB-List	PRESENCE optional}, 
	...
}

DRBsAdmittedList-ModConfirm-SNterminated ::= SEQUENCE (SIZE(1..maxnoofDRBs)) OF 
																				DRBsAdmittedList-ModConfirm-SNterminated-Item

DRBsAdmittedList-ModConfirm-SNterminated-Item ::= SEQUENCE {
	drb-ID											DRB-ID, 
	mN-DL-CG-UP-TNLInfo								UPTransportParameters							OPTIONAL, 
	secondary-MN-DL-CG-UP-TNLInfo					UPTransportParameters							OPTIONAL, 
	lCID											LCID											OPTIONAL, 
	iE-Extensions				ProtocolExtensionContainer { {DRBsAdmittedList-ModConfirm-SNterminated-Item-ExtIEs} } 	OPTIONAL, 
	...
}

DRBsAdmittedList-ModConfirm-SNterminated-Item-ExtIEs XNAP-PROTOCOL-EXTENSION ::= {
	{ ID id-Additional-PDCP-Duplication-TNL-List		CRITICALITY ignore	EXTENSION Additional-PDCP-Duplication-TNL-List	PRESENCE optional}, 
	...
}







PDUSessionResourceModRqdInfo-MNterminated ::= SEQUENCE {
	dRBsToBeModified				DRBsToBeModified-List-ModRqd-MNterminated				OPTIONAL, 
	dRBsToBeReleased				DRB-List-withCause											OPTIONAL, 
	iE-Extensions					ProtocolExtensionContainer { {PDUSessionResourceModRqdInfo-MNterminated-ExtIEs} } 	OPTIONAL, 
	...
}

PDUSessionResourceModRqdInfo-MNterminated-ExtIEs XNAP-PROTOCOL-EXTENSION ::= {
	...
}


DRBsToBeModified-List-ModRqd-MNterminated ::= SEQUENCE (SIZE(1..maxnoofDRBs)) OF DRBsToBeModified-List-ModRqd-MNterminated-Item

DRBsToBeModified-List-ModRqd-MNterminated-Item ::= SEQUENCE {
	drb-ID								DRB-ID, 
	sN-DL-SCG-UP-TNLInfo				UPTransportLayerInformation, 
	secondary-SN-DL-SCG-UP-TNLInfo		UPTransportLayerInformation		OPTIONAL, 
	lCID								LCID							OPTIONAL, 
	rlc-status							RLC-Status						OPTIONAL, 
	iE-Extensions					ProtocolExtensionContainer { {DRBsToBeModified-List-ModRqd-MNterminated-Item-ExtIEs} } OPTIONAL, 
	...
}

DRBsToBeModified-List-ModRqd-MNterminated-Item-ExtIEs XNAP-PROTOCOL-EXTENSION ::= {
	{ ID id-Additional-PDCP-Duplication-TNL-List		CRITICALITY ignore	EXTENSION Additional-PDCP-Duplication-TNL-List	PRESENCE optional}, 
	...
}







PDUSessionResourceModConfirmInfo-MNterminated ::= SEQUENCE {
	iE-Extensions					ProtocolExtensionContainer { {PDUSessionResourceModConfirmInfo-MNterminated-ExtIEs} } 	OPTIONAL, 
	...
}

PDUSessionResourceModConfirmInfo-MNterminated-ExtIEs XNAP-PROTOCOL-EXTENSION ::= {
	...
}






PDUSessionResourceBearerSetupCompleteInfo-SNterminated ::= SEQUENCE {
	dRBsToBeSetupList 			SEQUENCE (SIZE(1..maxnoofDRBs)) OF DRBsToBeSetupList-BearerSetupComplete-SNterminated-Item, 
	iE-Extensions				ProtocolExtensionContainer { {PDUSessionResourceBearerSetupCompleteInfo-SNterminated-ExtIEs} } 	OPTIONAL, 
	...
}

PDUSessionResourceBearerSetupCompleteInfo-SNterminated-ExtIEs XNAP-PROTOCOL-EXTENSION ::= {
	...
}

DRBsToBeSetupList-BearerSetupComplete-SNterminated-Item ::= SEQUENCE {
	dRB-ID						DRB-ID, 
	mN-Xn-U-TNLInfoatM			UPTransportLayerInformation, 
	iE-Extensions				ProtocolExtensionContainer { {DRBsToBeSetupList-BearerSetupComplete-SNterminated-Item-ExtIEs} } 	OPTIONAL, 
	...
}

DRBsToBeSetupList-BearerSetupComplete-SNterminated-Item-ExtIEs XNAP-PROTOCOL-EXTENSION ::= {
	{ID id-Secondary-MN-Xn-U-TNLInfoatM	CRITICALITY ignore	EXTENSION UPTransportLayerInformation		PRESENCE optional}, 
	...
}






PDUSessionResourceSecondaryRATUsageList ::= SEQUENCE (SIZE(1..maxnoofPDUSessions)) OF PDUSessionResourceSecondaryRATUsageItem

PDUSessionResourceSecondaryRATUsageItem ::= SEQUENCE {
	pDUSessionID								PDUSession-ID, 
	secondaryRATUsageInformation						SecondaryRATUsageInformation, 
	iE-Extensions		ProtocolExtensionContainer { {PDUSessionResourceSecondaryRATUsageItem-ExtIEs} }	OPTIONAL, 
	...
}

PDUSessionResourceSecondaryRATUsageItem-ExtIEs XNAP-PROTOCOL-EXTENSION ::= {
	...
}

PDUSessionUsageReport ::= SEQUENCE {
	rATType								ENUMERATED {nr,  eutra,  ...,  nr-unlicensed,  e-utra-unlicensed}, 
	pDUSessionTimedReportList			VolumeTimedReportList, 
	iE-Extensions						ProtocolExtensionContainer { {PDUSessionUsageReport-ExtIEs} } OPTIONAL, 
...
}

PDUSessionUsageReport-ExtIEs XNAP-PROTOCOL-EXTENSION ::= {
	...
}

PDUSessionType ::= ENUMERATED {ipv4,  ipv6,  ipv4v6,  ethernet,  unstructured,  ...}

PDUSession-ID	::= INTEGER (0..255)

PDUSessionNetworkInstance	::= INTEGER (1..256,  ...)

PDUSessionCommonNetworkInstance	::= OCTET STRING

Periodical ::= SEQUENCE {
	iE-Extensions		ProtocolExtensionContainer { { Periodical-ExtIEs} } OPTIONAL, 
	...
}

Periodical-ExtIEs XNAP-PROTOCOL-EXTENSION ::= {
	...
}


PLMN-Identity ::= OCTET STRING (SIZE(3))

PCIListForMDT ::= SEQUENCE (SIZE(1.. maxnoofNeighPCIforMDT)) OF NRPCI


PNI-NPN-Restricted-Information ::= ENUMERATED { restriced,  not-restricted,  ...}

PortNumber ::= BIT STRING (SIZE (16))

PriorityLevelQoS ::= INTEGER (1..127,  ...)


ProtectedE-UTRAResourceIndication ::= SEQUENCE {
	activationSFN					ActivationSFN, 
	protectedResourceList			ProtectedE-UTRAResourceList, 
	mbsfnControlRegionLength		MBSFNControlRegionLength					OPTIONAL, 
	pDCCHRegionLength				INTEGER (1..3), 
	iE-Extensions					ProtocolExtensionContainer { {ProtectedE-UTRAResourceIndication-ExtIEs} } 	OPTIONAL, 
	...
}

ProtectedE-UTRAResourceIndication-ExtIEs XNAP-PROTOCOL-EXTENSION ::= {
	...
}

ProtectedE-UTRAResourceList ::= SEQUENCE (SIZE (1.. maxnoofProtectedResourcePatterns)) OF ProtectedE-UTRAResource-Item

ProtectedE-UTRAResource-Item ::= SEQUENCE {
	resourceType							ENUMERATED {downlinknonCRS,  cRS,  uplink,  ...}, 
	intra-PRBProtectedResourceFootprint		BIT STRING (SIZE(84,  ...)), 
	protectedFootprintFrequencyPattern		BIT STRING (SIZE(6..110,  ...)), 
	protectedFootprintTimePattern			ProtectedE-UTRAFootprintTimePattern, 
	iE-Extensions					ProtocolExtensionContainer { {ProtectedE-UTRAResource-Item-ExtIEs} } 	OPTIONAL, 
	...
}

ProtectedE-UTRAResource-Item-ExtIEs XNAP-PROTOCOL-EXTENSION ::= {
	...
}


ProtectedE-UTRAFootprintTimePattern ::= SEQUENCE {
	protectedFootprintTimeperiodicity			INTEGER (1..320,  ...), 
	protectedFootrpintStartTime					INTEGER (1..20,  ...), 
	iE-Extensions					ProtocolExtensionContainer { {ProtectedE-UTRAFootprintTimePattern-ExtIEs} } 	OPTIONAL, 
	...
}

ProtectedE-UTRAFootprintTimePattern-ExtIEs XNAP-PROTOCOL-EXTENSION ::= {
	...
}



QoSCharacteristics ::= CHOICE {
	non-dynamic						NonDynamic5QIDescriptor, 
	dynamic							Dynamic5QIDescriptor, 
	choice-extension				ProtocolIE-Single-Container { {QoSCharacteristics-ExtIEs} }
}

QoSCharacteristics-ExtIEs XNAP-PROTOCOL-IES ::= {
	...
}


QoSFlowIdentifier	::= INTEGER (0..63,  ...)


QoSFlowLevelQoSParameters ::= SEQUENCE {
	qos-characteristics			QoSCharacteristics, 
	allocationAndRetentionPrio	AllocationandRetentionPriority, 
	gBRQoSFlowInfo				GBRQoSFlowInfo														OPTIONAL, 
	relectiveQoS				ReflectiveQoSAttribute												OPTIONAL, 
	additionalQoSflowInfo		ENUMERATED {more-likely,  ...}										OPTIONAL, 
	iE-Extensions				ProtocolExtensionContainer { {QoSFlowLevelQoSParameters-ExtIEs} } OPTIONAL, 
	...
}

QoSFlowLevelQoSParameters-ExtIEs XNAP-PROTOCOL-EXTENSION ::= {
	{ID id-QoSMonitoringRequest	CRITICALITY ignore	EXTENSION QosMonitoringRequest	PRESENCE optional}, 
	...
}


QoSFlowMappingIndication ::= ENUMERATED {
	ul, 
	dl, 
	...
}


QoSFlowNotificationControlIndicationInfo ::= SEQUENCE (SIZE (1..maxnoofQoSFlows)) OF QoSFlowNotify-Item

QoSFlowNotify-Item ::= SEQUENCE {
	qosFlowIdentifier			QoSFlowIdentifier, 
	notificationInformation		ENUMERATED {fulfilled,  not-fulfilled,  ...}, 
	iE-Extensions				ProtocolExtensionContainer { {QoSFlowNotificationControlIndicationInfo-ExtIEs} } OPTIONAL, 
	...
}

QoSFlowNotificationControlIndicationInfo-ExtIEs XNAP-PROTOCOL-EXTENSION ::= {
{	ID id-CurrentQoSParaSetIndex	CRITICALITY ignore	EXTENSION QoSParaSetNotifyIndex	PRESENCE optional }, 
	...
}


QoSFlows-List ::= SEQUENCE (SIZE (1..maxnoofQoSFlows)) OF QoSFlow-Item

QoSFlow-Item ::= SEQUENCE {
	qfi								QoSFlowIdentifier, 
	qosFlowMappingIndication		QoSFlowMappingIndication					OPTIONAL, 
	iE-Extension		ProtocolExtensionContainer { {QoSFlow-Item-ExtIEs} }	OPTIONAL, 
	...
}

QoSFlow-Item-ExtIEs XNAP-PROTOCOL-EXTENSION ::= {
	...
}


QoSFlows-List-withCause ::= SEQUENCE (SIZE (1..maxnoofQoSFlows)) OF QoSFlowwithCause-Item

QoSFlowwithCause-Item ::= SEQUENCE {
	qfi					QoSFlowIdentifier, 
	cause				Cause					OPTIONAL, 
	iE-Extension		ProtocolExtensionContainer { {QoSFlowwithCause-Item-ExtIEs} }	OPTIONAL, 
	...
}

QoSFlowwithCause-Item-ExtIEs XNAP-PROTOCOL-EXTENSION ::= {
	...
}

QoSParaSetIndex ::= INTEGER (1..8, ...) 
QoSParaSetNotifyIndex ::= INTEGER (0..8, ...)


QoSFlowsAdmitted-List ::= SEQUENCE (SIZE (1..maxnoofQoSFlows)) OF QoSFlowsAdmitted-Item

QoSFlowsAdmitted-Item ::= SEQUENCE {
	qfi								QoSFlowIdentifier, 
	iE-Extension		ProtocolExtensionContainer { {QoSFlowsAdmitted-Item-ExtIEs} }	OPTIONAL, 
	...
}

QoSFlowsAdmitted-Item-ExtIEs XNAP-PROTOCOL-EXTENSION ::= {
{ ID id-CurrentQoSParaSetIndex	CRITICALITY ignore	EXTENSION QoSParaSetIndex	PRESENCE optional	}, 
	...
}


QoSFlowsToBeSetup-List ::= SEQUENCE (SIZE (1..maxnoofQoSFlows)) OF QoSFlowsToBeSetup-Item

QoSFlowsToBeSetup-Item ::= SEQUENCE {
	qfi								QoSFlowIdentifier, 
	qosFlowLevelQoSParameters		QoSFlowLevelQoSParameters, 
	e-RAB-ID						E-RAB-ID											OPTIONAL, 
	iE-Extension		ProtocolExtensionContainer { {QoSFlowsToBeSetup-Item-ExtIEs} }	OPTIONAL, 
	...
}

QoSFlowsToBeSetup-Item-ExtIEs XNAP-PROTOCOL-EXTENSION ::= {
	{ ID id-TSCTrafficCharacteristics		CRITICALITY ignore	EXTENSION TSCTrafficCharacteristics 	PRESENCE optional}|
	{ ID id-RedundantQoSFlowIndicator		CRITICALITY ignore	EXTENSION RedundantQoSFlowIndicator	PRESENCE optional}, 
	...
}

QoSFlowsUsageReportList ::= SEQUENCE (SIZE(1..maxnoofQoSFlows)) OF QoSFlowsUsageReport-Item

QoSFlowsUsageReport-Item ::= SEQUENCE {
	qosFlowIdentifier					QoSFlowIdentifier, 
	rATType								ENUMERATED {nr,  eutra,  ...,  nr-unlicensed,  e-utra-unlicensed}, 
	qoSFlowsTimedReportList				VolumeTimedReportList, 
	iE-Extensions						ProtocolExtensionContainer { {QoSFlowsUsageReport-Item-ExtIEs} } OPTIONAL, 
...
}

QoSFlowsUsageReport-Item-ExtIEs XNAP-PROTOCOL-EXTENSION ::= {
	...
}

QosMonitoringRequest ::= ENUMERATED {ul,  dl,  both}


RACHReportInformation	::= SEQUENCE (SIZE(1.. maxnoofRACHReports)) OF RACHReportList-Item
RACHReportList-Item	::= SEQUENCE {
	rACHReport				RACHReportContainer, 
	iE-Extensions						ProtocolExtensionContainer { { RACHReportList-Item-ExtIEs} }	OPTIONAL, 
	...
}

RACHReportList-Item-ExtIEs XNAP-PROTOCOL-EXTENSION ::= {
	...
}

RACHReportContainer	::= OCTET STRING


RadioResourceStatus	::= CHOICE {
	ng-eNB-RadioResourceStatus	NG-eNB-RadioResourceStatus, 
	gNB-RadioResourceStatus	        GNB-RadioResourceStatus, 
	choice-extension			ProtocolIE-Single-Container { { RadioResourceStatus-ExtIEs} }

}

RadioResourceStatus-ExtIEs XNAP-PROTOCOL-IES ::= {
	...
}


RANAC ::= INTEGER (0..255)


RANAreaID ::= SEQUENCE {
	tAC					TAC, 
	rANAC				RANAC												OPTIONAL, 
	iE-Extensions		ProtocolExtensionContainer { {RANAreaID-ExtIEs} } 	OPTIONAL, 
	...
}

RANAreaID-ExtIEs XNAP-PROTOCOL-EXTENSION ::= {
	...
}


RANAreaID-List ::= SEQUENCE (SIZE(1..maxnoofRANAreasinRNA)) OF RANAreaID

Range ::= ENUMERATED {m50,  m80,  m180,  m200,  m350,  m400,  m500,  m700,  m1000,  ...}

RANPagingArea ::= SEQUENCE {
	pLMN-Identity			PLMN-Identity, 
	rANPagingAreaChoice		RANPagingAreaChoice, 
	iE-Extensions			ProtocolExtensionContainer { {RANPagingArea-ExtIEs} } OPTIONAL, 
	...
}

RANPagingArea-ExtIEs XNAP-PROTOCOL-EXTENSION ::= {
	...
}

RANPagingAreaChoice ::= CHOICE {
	cell-List			NG-RAN-Cell-Identity-ListinRANPagingArea, 
	rANAreaID-List		RANAreaID-List, 
	choice-extension	ProtocolIE-Single-Container { {RANPagingAreaChoice-ExtIEs} }
}

RANPagingAreaChoice-ExtIEs XNAP-PROTOCOL-IES ::= {
	...
}


RANPagingAttemptInfo ::= SEQUENCE {
	pagingAttemptCount					INTEGER (1..16,  ...), 
	intendedNumberOfPagingAttempts		INTEGER (1..16,  ...), 
	nextPagingAreaScope					ENUMERATED {same,  changed,  ...}	OPTIONAL, 
	iE-Extensions			ProtocolExtensionContainer { {RANPagingAttemptInfo-ExtIEs} } OPTIONAL, 
	...
}

RANPagingAttemptInfo-ExtIEs XNAP-PROTOCOL-EXTENSION ::= {
	...
}

RANPagingFailure		::= 	ENUMERATED {
	true, 
	...
}

RedundantQoSFlowIndicator ::= ENUMERATED {true,  false}

RedundantPDUSessionInformation ::= SEQUENCE {
	rSN					RSN, 
	iE-Extensions		ProtocolExtensionContainer { {RedundantPDUSessionInformation-ExtIEs} }	OPTIONAL, 
	...
}

RedundantPDUSessionInformation-ExtIEs XNAP-PROTOCOL-EXTENSION ::= {
	...
}

RSN ::= ENUMERATED {v1,  v2,  ...}

ReferenceID ::= INTEGER (1..64,  ...)


ReflectiveQoSAttribute ::= ENUMERATED {subject-to-reflective-QoS,  ...}

ReportAmountMDT ::= ENUMERATED{r1,  r2,  r4,  r8,  r16,  r32,  r64,  infinity,  ...}


ReportArea ::= ENUMERATED {
	cell, 
	...
}

ReportIntervalMDT ::= ENUMERATED {ms120,  ms240,  ms480,  ms640,  ms1024,  ms2048,  ms5120,  ms10240,  min1,  min6,  min12,  min30,  min60,  ...} 

ReportType ::= CHOICE {
	periodical					Periodical, 
	eventTriggered				EventTriggered, 
	...
}

ReportCharacteristics ::=  BIT STRING(SIZE(32))


ReportingPeriodicity ::= ENUMERATED {
	half-thousand-ms, 
one-thousand-ms, 
	two-thousand-ms, 
	five-thousand-ms, 
	ten-thousand-ms, 
...
}


RegistrationRequest ::= ENUMERATED {start,  stop,  add,  ... }

RequestReferenceID ::= INTEGER (1..64,  ...)


ReservedSubframePattern ::= SEQUENCE {
	subframeType					ENUMERATED {mbsfn,  non-mbsfn,  ...}, 
	reservedSubframePattern			BIT STRING (SIZE(10..160)), 
	mbsfnControlRegionLength		MBSFNControlRegionLength					OPTIONAL, 
	iE-Extension					ProtocolExtensionContainer { {ReservedSubframePattern-ExtIEs} } OPTIONAL, 
	...
}

ReservedSubframePattern-ExtIEs XNAP-PROTOCOL-EXTENSION ::= {
	...
}



ResetRequestTypeInfo ::= CHOICE {
	fullReset			ResetRequestTypeInfo-Full, 
	partialReset		ResetRequestTypeInfo-Partial, 
	choice-extension	ProtocolIE-Single-Container { {ResetRequestTypeInfo-ExtIEs} }
}

ResetRequestTypeInfo-ExtIEs XNAP-PROTOCOL-IES ::= {
	...
}

ResetRequestTypeInfo-Full ::= SEQUENCE {
	iE-Extension					ProtocolExtensionContainer { {ResetRequestTypeInfo-Full-ExtIEs} } OPTIONAL, 
	...
}

ResetRequestTypeInfo-Full-ExtIEs XNAP-PROTOCOL-EXTENSION ::= {
	...
}

ResetRequestTypeInfo-Partial ::= SEQUENCE {
	ue-contexts-ToBeReleasedList	ResetRequestPartialReleaseList, 
	iE-Extension					ProtocolExtensionContainer { {ResetRequestTypeInfo-Partial-ExtIEs} } OPTIONAL, 
	...
}

ResetRequestTypeInfo-Partial-ExtIEs XNAP-PROTOCOL-EXTENSION ::= {
	...
}

ResetRequestPartialReleaseList ::= SEQUENCE (SIZE(1..maxnoofUEContexts)) OF ResetRequestPartialReleaseItem

ResetRequestPartialReleaseItem ::= SEQUENCE {
	ng-ran-node1UEXnAPID						NG-RANnodeUEXnAPID			OPTIONAL, 
	ng-ran-node2UEXnAPID						NG-RANnodeUEXnAPID			OPTIONAL, 
	iE-Extensions							ProtocolExtensionContainer { {ResetRequestPartialReleaseItem-ExtIEs} } OPTIONAL, 
	...
}

ResetRequestPartialReleaseItem-ExtIEs XNAP-PROTOCOL-EXTENSION ::= {
	...
}


ResetResponseTypeInfo ::= CHOICE {
	fullReset			ResetResponseTypeInfo-Full, 
	partialReset		ResetResponseTypeInfo-Partial, 
	choice-extension	ProtocolIE-Single-Container { {ResetResponseTypeInfo-ExtIEs} }
}

ResetResponseTypeInfo-ExtIEs XNAP-PROTOCOL-IES ::= {
	...
}

ResetResponseTypeInfo-Full ::= SEQUENCE {
	iE-Extension					ProtocolExtensionContainer { {ResetResponseTypeInfo-Full-ExtIEs} } OPTIONAL, 
	...
}

ResetResponseTypeInfo-Full-ExtIEs XNAP-PROTOCOL-EXTENSION ::= {
	...
}

ResetResponseTypeInfo-Partial ::= SEQUENCE {
	ue-contexts-AdmittedToBeReleasedList	ResetResponsePartialReleaseList, 
	iE-Extension					ProtocolExtensionContainer { {ResetResponseTypeInfo-Partial-ExtIEs} } OPTIONAL, 
	...
}

ResetResponseTypeInfo-Partial-ExtIEs XNAP-PROTOCOL-EXTENSION ::= {
	...
}

ResetResponsePartialReleaseList ::= SEQUENCE (SIZE(1..maxnoofUEContexts)) OF ResetResponsePartialReleaseItem

ResetResponsePartialReleaseItem ::= SEQUENCE {
	ng-ran-node1UEXnAPID						NG-RANnodeUEXnAPID		OPTIONAL, 
	ng-ran-node2UEXnAPID						NG-RANnodeUEXnAPID		OPTIONAL, 
	iE-Extensions							ProtocolExtensionContainer { {ResetResponsePartialReleaseItem-ExtIEs} } OPTIONAL, 
	...
}

ResetResponsePartialReleaseItem-ExtIEs XNAP-PROTOCOL-EXTENSION ::= {
	...
}


RLCMode	::= ENUMERATED {
	rlc-am, 
	rlc-um-bidirectional, 
	rlc-um-unidirectional-ul, 
	rlc-um-unidirectional-dl, 
	...
	}


RLC-Status ::= SEQUENCE {
	reestablishment-Indication 	Reestablishment-Indication, 
	iE-Extensions					ProtocolExtensionContainer { {RLC-Status-ExtIEs} } OPTIONAL, 
	...
}

RLC-Status-ExtIEs XNAP-PROTOCOL-EXTENSION ::= {
	...
}

RLCDuplicationInformation ::= 		SEQUENCE {
	rLCDuplicationStateList 		RLCDuplicationStateList, 
	rLC-PrimaryIndicator 		ENUMERATED {true,  false}		OPTIONAL, 
	iE-Extensions					ProtocolExtensionContainer { {RLCDuplicationInformation-ItemExtIEs} }	OPTIONAL
}

RLCDuplicationInformation-ItemExtIEs 	XNAP-PROTOCOL-EXTENSION ::= {
	...
}

RLCDuplicationStateList	::= 	SEQUENCE (SIZE(1..maxnoofRLCDuplicationstate)) OF RLCDuplicationState-Item

RLCDuplicationState-Item ::=	SEQUENCE {
	duplicationState			ENUMERATED {active, inactive,  ...},  
	iE-Extensions	ProtocolExtensionContainer { {RLCDuplicationState-ItemExtIEs } }	OPTIONAL, 
	...
}

RLCDuplicationState-ItemExtIEs XNAP-PROTOCOL-EXTENSION ::= {
	...
}

Reestablishment-Indication ::= ENUMERATED {
	reestablished, 
	...
}


RFSP-Index ::= INTEGER (1..256)


RRCConfigIndication ::= ENUMERATED {
	full-config, 
	delta-config, 
	...
}

RRCConnections::= SEQUENCE {
	noofRRCConnections                   	NoofRRCConnections, 
	availableRRCConnectionCapacityValue	AvailableRRCConnectionCapacityValue, 
	iE-Extensions				ProtocolExtensionContainer { { RRCConnections-ExtIEs} }	OPTIONAL, 
	...
}

RRCConnections-ExtIEs XNAP-PROTOCOL-EXTENSION ::= {
	...
}


RRCReestab-initiated ::= SEQUENCE {
	failureCellPCI    NG-RAN-CellPCI	,
reestabCellCGI    GlobalNG-RANCell-ID,
c-RNTI            C-RNTI,
shortMAC-I        MAC-I,
uERLFReportContainer        UERLFReportContainer			OPTIONAL, 
	iE-Extensions			ProtocolExtensionContainer { { RRCReestab-initiated-ExtIEs} } OPTIONAL, 
	...
}

RRCReestab-initiated-ExtIEs XNAP-PROTOCOL-EXTENSION ::= {
	...
}


RRCSetup-initiated ::= SEQUENCE {
	uERLFReportContainer    UERLFReportContainer			OPTIONAL, 
	iE-Extensions			ProtocolExtensionContainer { { RRCSetup-initiated-ExtIEs} } OPTIONAL, 
	...
}

RRCSetup-initiated-ExtIEs XNAP-PROTOCOL-EXTENSION ::= {
	...
}

RRCResumeCause ::= ENUMERATED {
	rna-Update, 
	...
}


SecondarydataForwardingInfoFromTarget-Item::= SEQUENCE {
	secondarydataForwardingInfoFromTarget				DataForwardingInfoFromTargetNGRANnode, 
	iE-Extensions		ProtocolExtensionContainer { { SecondarydataForwardingInfoFromTarget-Item-ExtIEs} }	OPTIONAL, 
	...
}

SecondarydataForwardingInfoFromTarget-Item-ExtIEs XNAP-PROTOCOL-EXTENSION ::= {
	...
}

SecondarydataForwardingInfoFromTarget-List ::= SEQUENCE (SIZE(1..maxnoofMultiConnectivityMinusOne)) OF SecondarydataForwardingInfoFromTarget-Item

SCGConfigurationQuery	::= ENUMERATED {true,  ...}

SecondaryRATUsageInformation ::= SEQUENCE {
	pDUSessionUsageReport		PDUSessionUsageReport				OPTIONAL, 
	qosFlowsUsageReportList		QoSFlowsUsageReportList				OPTIONAL, 
	iE-Extension				ProtocolExtensionContainer { {SecondaryRATUsageInformation-ExtIEs} }	OPTIONAL, 
	...
}

SecondaryRATUsageInformation-ExtIEs XNAP-PROTOCOL-EXTENSION ::= {
	...
}

SecurityIndication ::= SEQUENCE {
	integrityProtectionIndication			ENUMERATED {required,  preferred,  not-needed,  ...}, 
	confidentialityProtectionIndication		ENUMERATED {required,  preferred,  not-needed,  ...}, 
	maximumIPdatarate						MaximumIPdatarate												OPTIONAL, 

	iE-Extensions							ProtocolExtensionContainer { {SecurityIndication-ExtIEs} } OPTIONAL, 
	...
}

SecurityIndication-ExtIEs XNAP-PROTOCOL-EXTENSION ::= {
	...
}


SecurityResult ::= SEQUENCE {
	integrityProtectionResult				ENUMERATED {performed,  not-performed,  ...}, 
	confidentialityProtectionResult			ENUMERATED {performed,  not-performed,  ...}, 
	iE-Extensions							ProtocolExtensionContainer { {SecurityResult-ExtIEs} } OPTIONAL, 
	...
}

SecurityResult-ExtIEs XNAP-PROTOCOL-EXTENSION ::= {
	...
}

SensorMeasurementConfiguration ::= SEQUENCE {
	sensorMeasConfig 				SensorMeasConfig, 
	sensorMeasConfigNameList		SensorMeasConfigNameList            OPTIONAL, 
	iE-Extensions		ProtocolExtensionContainer { { SensorMeasurementConfiguration-ExtIEs } } OPTIONAL, 
	...
}

SensorMeasurementConfiguration-ExtIEs XNAP-PROTOCOL-EXTENSION ::= {
	...
}

SensorMeasConfigNameList ::= SEQUENCE (SIZE(1..maxnoofSensorName)) OF SensorName

SensorMeasConfig::= ENUMERATED {setup, ...}

SensorName ::= SEQUENCE {
	uncompensatedBarometricConfig	ENUMERATED {true,  ...}         OPTIONAL, 
	ueSpeedConfig					ENUMERATED {true,  ...}         OPTIONAL, 
	ueOrientationConfig				ENUMERATED {true,  ...}         OPTIONAL, 
	iE-Extensions				ProtocolExtensionContainer { {SensorNameConfig-ExtIEs} } OPTIONAL, 
...
}
   
SensorNameConfig-ExtIEs XNAP-PROTOCOL-EXTENSION ::= {
	...
}



ServedCellInformation-E-UTRA ::= SEQUENCE {
	e-utra-pci								E-UTRAPCI, 
	e-utra-cgi								E-UTRA-CGI, 
	tac										TAC, 
	ranac									RANAC																					OPTIONAL, 
	broadcastPLMNs							SEQUENCE (SIZE(1..maxnoofBPLMNs)) OF ServedCellInformation-E-UTRA-perBPLMN, 
	e-utra-mode-info						ServedCellInformation-E-UTRA-ModeInfo, 
	numberofAntennaPorts					NumberOfAntennaPorts-E-UTRA																OPTIONAL, 
	prach-configuration						E-UTRAPRACHConfiguration																OPTIONAL, 
	mBSFNsubframeInfo						MBSFNSubframeInfo-E-UTRA																OPTIONAL, 
	multibandInfo							E-UTRAMultibandInfoList																	OPTIONAL, 
	freqBandIndicatorPriority				ENUMERATED {not-broadcast,  broadcast,  ...} 												OPTIONAL, 
	bandwidthReducedSI						ENUMERATED {scheduled,  ...}																OPTIONAL, 
	protectedE-UTRAResourceIndication		ProtectedE-UTRAResourceIndication														OPTIONAL, 
	iE-Extensions				ProtocolExtensionContainer { {ServedCellInformation-E-UTRA-ExtIEs} }					OPTIONAL, 
	...
}

ServedCellInformation-E-UTRA-ExtIEs XNAP-PROTOCOL-EXTENSION ::= {
	{ ID id-BPLMN-ID-Info-EUTRA		CRITICALITY ignore	EXTENSION BPLMN-ID-Info-EUTRA		PRESENCE optional }, 
	...
}


ServedCellInformation-E-UTRA-perBPLMN ::= SEQUENCE {
	plmn-id					PLMN-Identity, 
	iE-Extensions			ProtocolExtensionContainer { {ServedCellInformation-E-UTRA-perBPLMN-ExtIEs} } OPTIONAL, 
	...
}

ServedCellInformation-E-UTRA-perBPLMN-ExtIEs XNAP-PROTOCOL-EXTENSION ::= {
	...
}


ServedCellInformation-E-UTRA-ModeInfo ::= CHOICE {
	fdd					ServedCellInformation-E-UTRA-FDDInfo, 
	tdd					ServedCellInformation-E-UTRA-TDDInfo, 
	choice-extension	ProtocolIE-Single-Container{ {ServedCellInformation-E-UTRA-ModeInfo-ExtIEs} }
}

ServedCellInformation-E-UTRA-ModeInfo-ExtIEs XNAP-PROTOCOL-IES ::= {
	...
}


ServedCellInformation-E-UTRA-FDDInfo ::= SEQUENCE {
	ul-earfcn			E-UTRAARFCN, 
	dl-earfcn			E-UTRAARFCN, 
	ul-e-utraTxBW		E-UTRATransmissionBandwidth, 
	dl-e-utraTxBW		E-UTRATransmissionBandwidth, 
	iE-Extensions		ProtocolExtensionContainer { {ServedCellInformation-E-UTRA-FDDInfo-ExtIEs} } OPTIONAL, 
	...
}

ServedCellInformation-E-UTRA-FDDInfo-ExtIEs XNAP-PROTOCOL-EXTENSION ::= {
	{ ID id-OffsetOfNbiotChannelNumberToDL-EARFCN	CRITICALITY reject	EXTENSION OffsetOfNbiotChannelNumberToEARFCN		PRESENCE optional}|
	{ ID id-OffsetOfNbiotChannelNumberToUL-EARFCN	CRITICALITY reject	EXTENSION OffsetOfNbiotChannelNumberToEARFCN		PRESENCE optional}, 
	...
}


ServedCellInformation-E-UTRA-TDDInfo ::= SEQUENCE {
	earfcn					E-UTRAARFCN, 
	e-utraTxBW				E-UTRATransmissionBandwidth, 
	subframeAssignmnet		ENUMERATED {sa0, sa1, sa2, sa3, sa4, sa5, sa6, ...}, 
	specialSubframeInfo		SpecialSubframeInfo-E-UTRA, 
	iE-Extensions			ProtocolExtensionContainer { {ServedCellInformation-E-UTRA-TDDInfo-ExtIEs} } OPTIONAL, 
	...
}

ServedCellInformation-E-UTRA-TDDInfo-ExtIEs XNAP-PROTOCOL-EXTENSION ::= {
	{ ID id-OffsetOfNbiotChannelNumberToDL-EARFCN	CRITICALITY reject	EXTENSION OffsetOfNbiotChannelNumberToEARFCN		PRESENCE optional}|
	{ ID id-NBIoT-UL-DL-AlignmentOffset				CRITICALITY reject	EXTENSION NBIoT-UL-DL-AlignmentOffset					PRESENCE optional}, 
	...
}


ServedCells-E-UTRA ::= SEQUENCE (SIZE (1..maxnoofCellsinNG-RANnode)) OF ServedCells-E-UTRA-Item

ServedCells-E-UTRA-Item ::= SEQUENCE {
	served-cell-info-E-UTRA		ServedCellInformation-E-UTRA, 
	neighbour-info-NR			NeighbourInformation-NR									OPTIONAL, 
	neighbour-info-E-UTRA		NeighbourInformation-E-UTRA								OPTIONAL, 
	iE-Extensions		ProtocolExtensionContainer { {ServedCells-E-UTRA-Item-ExtIEs} } OPTIONAL, 
	...
}

ServedCells-E-UTRA-Item-ExtIEs XNAP-PROTOCOL-EXTENSION ::= {
	...
}


ServedCellsToUpdate-E-UTRA ::= SEQUENCE {
	served-Cells-ToAdd-E-UTRA		ServedCells-E-UTRA																OPTIONAL, 
	served-Cells-ToModify-E-UTRA	ServedCells-ToModify-E-UTRA														OPTIONAL, 
	served-Cells-ToDelete-E-UTRA	SEQUENCE (SIZE (1..maxnoofCellsinNG-RANnode)) OF E-UTRA-CGI 					OPTIONAL, 
iE-Extensions					ProtocolExtensionContainer { {ServedCellsToUpdate-E-UTRA-ExtIEs} }	OPTIONAL, 
	...
}

ServedCellsToUpdate-E-UTRA-ExtIEs XNAP-PROTOCOL-EXTENSION ::= {
	...
}


ServedCells-ToModify-E-UTRA ::= SEQUENCE (SIZE (1..maxnoofCellsinNG-RANnode)) OF ServedCells-ToModify-E-UTRA-Item

ServedCells-ToModify-E-UTRA-Item ::= SEQUENCE {
	old-ECGI					E-UTRA-CGI, 
	served-cell-info-E-UTRA		ServedCellInformation-E-UTRA, 
	neighbour-info-NR			NeighbourInformation-NR											OPTIONAL, 
	neighbour-info-E-UTRA		NeighbourInformation-E-UTRA										OPTIONAL, 
	deactivation-indication		ENUMERATED {deactivated,  ...}									OPTIONAL, 
	iE-Extensions		ProtocolExtensionContainer { {Served-cells-ToModify-E-UTRA-Item-ExtIEs} }	OPTIONAL, 
	...
}

Served-cells-ToModify-E-UTRA-Item-ExtIEs XNAP-PROTOCOL-EXTENSION ::= {
	...
}



ServedCellInformation-NR ::= SEQUENCE {
	nrPCI								NRPCI, 
	cellID								NR-CGI, 
	tac									TAC, 
	ranac								RANAC						OPTIONAL, 
	broadcastPLMN						BroadcastPLMNs, 
	nrModeInfo							NRModeInfo, 
	measurementTimingConfiguration		OCTET STRING, 
	connectivitySupport					Connectivity-Support, 	
	iE-Extensions						ProtocolExtensionContainer { {ServedCellInformation-NR-ExtIEs} } OPTIONAL, 
	...
}

ServedCellInformation-NR-ExtIEs XNAP-PROTOCOL-EXTENSION ::= {
	{ ID id-BPLMN-ID-Info-NR			CRITICALITY ignore	EXTENSION BPLMN-ID-Info-NR				PRESENCE optional }|
	{ ID id-SSB-PositionsInBurst	CRITICALITY ignore	EXTENSION SSB-PositionsInBurst	PRESENCE optional }|
	{ ID id-NRCellPRACHConfig		CRITICALITY ignore	EXTENSION NRCellPRACHConfig		PRESENCE optional }|
	{ ID id-NPN-Broadcast-Information	CRITICALITY reject	EXTENSION NPN-Broadcast-Information		PRESENCE optional }|
	{ ID id-CSI-RSTransmissionIndication	CRITICALITY ignore	EXTENSION CSI-RSTransmissionIndication		PRESENCE optional }, 
	...
}


ServedCells-NR ::= SEQUENCE (SIZE (1..maxnoofCellsinNG-RANnode)) OF ServedCells-NR-Item

ServedCells-NR-Item ::= SEQUENCE {
	served-cell-info-NR			ServedCellInformation-NR, 
	neighbour-info-NR			NeighbourInformation-NR				OPTIONAL, 
	neighbour-info-E-UTRA		NeighbourInformation-E-UTRA			OPTIONAL, 
	iE-Extensions		ProtocolExtensionContainer { {ServedCells-NR-Item-ExtIEs} } OPTIONAL, 
	...
}

ServedCells-NR-Item-ExtIEs XNAP-PROTOCOL-EXTENSION ::= {
	...
}


ServedCells-ToModify-NR ::= SEQUENCE (SIZE (1..maxnoofCellsinNG-RANnode)) OF ServedCells-ToModify-NR-Item

ServedCells-ToModify-NR-Item ::= SEQUENCE {
	old-NR-CGI					NR-CGI, 
	served-cell-info-NR			ServedCellInformation-NR, 
	neighbour-info-NR			NeighbourInformation-NR				 							OPTIONAL, 
	neighbour-info-E-UTRA		NeighbourInformation-E-UTRA										OPTIONAL, 
	deactivation-indication		ENUMERATED {deactivated,  ...}									OPTIONAL, 
	iE-Extensions		ProtocolExtensionContainer { {Served-cells-ToModify-NR-Item-ExtIEs} } 	OPTIONAL, 
	...
}

Served-cells-ToModify-NR-Item-ExtIEs XNAP-PROTOCOL-EXTENSION ::= {
	...
}


ServedCellsToUpdate-NR ::= SEQUENCE {
	served-Cells-ToAdd-NR		ServedCells-NR															OPTIONAL, 
	served-Cells-ToModify-NR	ServedCells-ToModify-NR													OPTIONAL, 
	served-Cells-ToDelete-NR	SEQUENCE (SIZE (1..maxnoofCellsinNG-RANnode)) OF NR-CGI 				OPTIONAL, 
	iE-Extensions		ProtocolExtensionContainer { {ServedCellsToUpdate-NR-ExtIEs} } OPTIONAL, 
	...
}

ServedCellsToUpdate-NR-ExtIEs XNAP-PROTOCOL-EXTENSION ::= {
	...
}


ServingSNPNID ::= SEQUENCE {
	plmn-id							PLMN-Identity, 
	nid								NID, 
	iE-Extension					ProtocolExtensionContainer { {ServingSNPNID-ExtIEs} } OPTIONAL, 
	...
}

ServingSNPNID-ExtIEs XNAP-PROTOCOL-EXTENSION ::= {
	...
}


SharedResourceType ::= CHOICE {
	ul-onlySharing				SharedResourceType-UL-OnlySharing, 
	ul-and-dl-Sharing			SharedResourceType-ULDL-Sharing, 
	choice-extension			ProtocolIE-Single-Container { {SharedResourceType-ExtIEs} }
}

SharedResourceType-ExtIEs XNAP-PROTOCOL-IES ::= {
	...
}

SharedResourceType-UL-OnlySharing ::= SEQUENCE {
	ul-resourceBitmap			DataTrafficResources, 
	iE-Extensions			ProtocolExtensionContainer { {SharedResourceType-UL-OnlySharing-ExtIEs} } OPTIONAL, 
	...
}

SharedResourceType-UL-OnlySharing-ExtIEs XNAP-PROTOCOL-EXTENSION ::= {
	...
}

SharedResourceType-ULDL-Sharing ::= CHOICE {
	ul-resources				SharedResourceType-ULDL-Sharing-UL-Resources, 
	dl-resources				SharedResourceType-ULDL-Sharing-DL-Resources, 
	choice-extension			ProtocolIE-Single-Container { {SharedResourceType-ULDL-Sharing-ExtIEs} }
}

SharedResourceType-ULDL-Sharing-ExtIEs XNAP-PROTOCOL-IES ::= {
	...
}

SharedResourceType-ULDL-Sharing-UL-Resources ::= CHOICE {
	unchanged					NULL, 
	changed						SharedResourceType-ULDL-Sharing-UL-ResourcesChanged, 
	choice-extension			ProtocolIE-Single-Container { {SharedResourceType-ULDL-Sharing-UL-Resources-ExtIEs} }
}

SharedResourceType-ULDL-Sharing-UL-Resources-ExtIEs XNAP-PROTOCOL-IES ::= {
	...
}

SharedResourceType-ULDL-Sharing-UL-ResourcesChanged ::= SEQUENCE {
	ul-resourceBitmap			DataTrafficResources, 
	iE-Extensions			ProtocolExtensionContainer { {SharedResourceType-ULDL-Sharing-UL-ResourcesChanged-ExtIEs} } OPTIONAL, 
	...
}

SharedResourceType-ULDL-Sharing-UL-ResourcesChanged-ExtIEs XNAP-PROTOCOL-EXTENSION ::= {
	...
}

SharedResourceType-ULDL-Sharing-DL-Resources ::= CHOICE {
	unchanged					NULL, 
	changed						SharedResourceType-ULDL-Sharing-DL-ResourcesChanged, 
	choice-extension			ProtocolIE-Single-Container { {SharedResourceType-ULDL-Sharing-DL-Resources-ExtIEs} }
}

SharedResourceType-ULDL-Sharing-DL-Resources-ExtIEs XNAP-PROTOCOL-IES ::= {
	...
}

SharedResourceType-ULDL-Sharing-DL-ResourcesChanged ::= SEQUENCE {
	dl-resourceBitmap			DataTrafficResources, 
	iE-Extensions			ProtocolExtensionContainer { {SharedResourceType-ULDL-Sharing-DL-ResourcesChanged-ExtIEs} } OPTIONAL, 
	...
}

SharedResourceType-ULDL-Sharing-DL-ResourcesChanged-ExtIEs XNAP-PROTOCOL-EXTENSION ::= {
	...
}

SliceAvailableCapacity ::= SEQUENCE (SIZE(1..maxnoofBPLMNs)) OF SliceAvailableCapacity-Item

SliceAvailableCapacity-Item	::= SEQUENCE {
	pLMNIdentity						PLMN-Identity,  
	sNSSAIAvailableCapacity-List		SNSSAIAvailableCapacity-List, 
	iE-Extensions						ProtocolExtensionContainer { { SliceAvailableCapacity-Item-ExtIEs} }	OPTIONAL, 
	...
}


SliceAvailableCapacity-Item-ExtIEs XNAP-PROTOCOL-EXTENSION ::= {
	...
}

SNSSAIAvailableCapacity-List ::= SEQUENCE (SIZE(1.. maxnoofSliceItems)) OF SNSSAIAvailableCapacity-Item

SNSSAIAvailableCapacity-Item ::= SEQUENCE {
	sNSSAI		S-NSSAI, 
	sliceAvailableCapacityValueDownlink	INTEGER (0..100), 
	sliceAvailableCapacityValueUplink	INTEGER (0..100), 
	iE-Extensions				ProtocolExtensionContainer { { SNSSAIAvailableCapacity-Item-ExtIEs } }	OPTIONAL
}

SNSSAIAvailableCapacity-Item-ExtIEs	XNAP-PROTOCOL-EXTENSION ::= {
	...
}

SliceSupport-List	::= SEQUENCE (SIZE(1..maxnoofSliceItems)) OF S-NSSAI

SliceToReport-List ::= SEQUENCE (SIZE(1..maxnoofBPLMNs)) OF SliceToReport-List-Item

SliceToReport-List-Item	::= SEQUENCE {
	pLMNIdentity				PLMN-Identity,  
	sNSSAIlist					SNSSAI-list, 
	iE-Extensions						ProtocolExtensionContainer { { SliceToReport-List-Item-ExtIEs} }	OPTIONAL, 
	...
}


SliceToReport-List-Item-ExtIEs XNAP-PROTOCOL-EXTENSION ::= {
	...
}

SNSSAI-list ::= SEQUENCE (SIZE(1.. maxnoofSliceItems)) OF SNSSAI-Item

SNSSAI-Item ::= SEQUENCE {
	sNSSAI		S-NSSAI, 
	iE-Extensions				ProtocolExtensionContainer { { SNSSAI-Item-ExtIEs } }	OPTIONAL
}

SNSSAI-Item-ExtIEs	XNAP-PROTOCOL-EXTENSION ::= {
	...
}

SlotConfiguration-List ::= SEQUENCE (SIZE (1..maxnoofslots)) OF SlotConfiguration-List-Item

SlotConfiguration-List-Item ::= SEQUENCE {
	slotIndex						INTEGER (0..5119), 
	symbolAllocation-in-Slot		SymbolAllocation-in-Slot, 
	iE-Extensions				ProtocolExtensionContainer { {SlotConfiguration-List-Item-ExtIEs} }	OPTIONAL, 
	...
}

SlotConfiguration-List-Item-ExtIEs XNAP-PROTOCOL-EXTENSION ::= {
	...
}

S-NG-RANnode-SecurityKey ::= BIT STRING (SIZE(256))

S-NG-RANnode-Addition-Trigger-Ind ::= ENUMERATED {
	sn-change, 
	inter-MN-HO, 
	intra-MN-HO, 
	...
}

S-NSSAI ::= SEQUENCE {
	sst						OCTET STRING (SIZE(1)), 
	sd						OCTET STRING (SIZE(3))							OPTIONAL, 
	iE-Extensions			ProtocolExtensionContainer { {S-NSSAI-ExtIEs} } OPTIONAL, 
	...
}

S-NSSAI-ExtIEs XNAP-PROTOCOL-EXTENSION ::= {
	...
}

SNTriggered ::=ENUMERATED{
true, 
...  
}

SpecialSubframeInfo-E-UTRA ::= SEQUENCE {
	specialSubframePattern	SpecialSubframePatterns-E-UTRA, 
	cyclicPrefixDL			CyclicPrefix-E-UTRA-DL, 
	cyclicPrefixUL			CyclicPrefix-E-UTRA-UL, 
	iE-Extensions			ProtocolExtensionContainer { {SpecialSubframeInfo-E-UTRA-ExtIEs} } OPTIONAL, 
	...
}

SpecialSubframeInfo-E-UTRA-ExtIEs XNAP-PROTOCOL-EXTENSION ::= {
	...
}


SpecialSubframePatterns-E-UTRA ::= ENUMERATED {
	ssp0, 
	ssp1, 
	ssp2, 
	ssp3, 
	ssp4, 
	ssp5, 
	ssp6, 
	ssp7, 
	ssp8, 
	ssp9, 
	ssp10, 
	...
}


SpectrumSharingGroupID ::= INTEGER (1..maxnoofCellsinNG-RANnode)

SplitSessionIndicator ::= ENUMERATED {
	split, 
	...
}

SplitSRBsTypes ::= ENUMERATED {srb1,  srb2,  srb1and2,  ...}

SSBAreaCapacityValue-List ::= SEQUENCE (SIZE(1..maxnoofSSBAreas)) OF SSBAreaCapacityValue-List-Item

SSBAreaCapacityValue-List-Item	::= SEQUENCE {
sSBIndex				INTEGER(0..63), 
ssbAreaCapacityValue	INTEGER (0..100), 
	iE-Extensions						ProtocolExtensionContainer { { SSBAreaCapacityValue-List-Item-ExtIEs} }	OPTIONAL, 
	...
}


SSBAreaCapacityValue-List-Item-ExtIEs XNAP-PROTOCOL-EXTENSION ::= {
	...
}


SSBAreaRadioResourceStatus-List ::= SEQUENCE (SIZE(1..maxnoofSSBAreas)) OF SSBAreaRadioResourceStatus-List-Item

SSBAreaRadioResourceStatus-List-Item	::= SEQUENCE {
	sSBIndex								INTEGER(0..63), 
ssb-Area-DL-GBR-PRB-usage	DL-GBR-PRB-usage, 
ssb-Area-UL-GBR-PRB-usage	UL-GBR-PRB-usage, 
ssb-Area-dL-non-GBR-PRB-usage		DL-non-GBR-PRB-usage, 
	ssb-Area-uL-non-GBR-PRB-usage		UL-non-GBR-PRB-usage, 
	ssb-Area-dL-Total-PRB-usage			DL-Total-PRB-usage, 
	ssb-Area-uL-Total-PRB-usage			UL-Total-PRB-usage, 
	iE-Extensions						ProtocolExtensionContainer { { SSBAreaRadioResourceStatus-List-Item-ExtIEs} }	OPTIONAL, 
	...
}


SSBAreaRadioResourceStatus-List-Item-ExtIEs XNAP-PROTOCOL-EXTENSION ::= {
	...
}


SSB-PositionsInBurst ::= CHOICE {
	shortBitmap						BIT STRING (SIZE (4)), 
	mediumBitmap					BIT STRING (SIZE (8)), 
	longBitmap						BIT STRING (SIZE (64)), 
	choice-extension				ProtocolIE-Single-Container { {SSB-PositionsInBurst-ExtIEs} }
}

SSB-PositionsInBurst-ExtIEs XNAP-PROTOCOL-IES ::= {
	...
}


SSBToReport-List ::= SEQUENCE (SIZE(1..maxnoofSSBAreas)) OF SSBToReport-List-Item

SSBToReport-List-Item	::= SEQUENCE {
	sSBIndex				INTEGER(0..63), 
	iE-Extensions						ProtocolExtensionContainer { { SSBToReport-List-Item-ExtIEs} }	OPTIONAL, 
	...
}


SSBToReport-List-Item-ExtIEs XNAP-PROTOCOL-EXTENSION ::= {
	...
}


SUL-FrequencyBand ::= INTEGER (1..1024)


SUL-Information ::= SEQUENCE {
	sulFrequencyInfo			NRARFCN, 
	sulTransmissionBandwidth	NRTransmissionBandwidth, 
	iE-Extensions				ProtocolExtensionContainer { {SUL-Information-ExtIEs} } OPTIONAL, 
	...
}

SUL-Information-ExtIEs XNAP-PROTOCOL-EXTENSION ::= {
	{ ID id-CarrierList				CRITICALITY ignore	EXTENSION NRCarrierList			PRESENCE optional }|
	{ ID id-FrequencyShift7p5khz	CRITICALITY ignore	EXTENSION FrequencyShift7p5khz	PRESENCE optional }, 

...
}


SupportedSULBandList ::= SEQUENCE (SIZE(1..maxnoofNRCellBands)) OF SupportedSULBandItem

SupportedSULBandItem ::= SEQUENCE {
	sulBandItem					SUL-FrequencyBand, 
	iE-Extensions				ProtocolExtensionContainer { {SupportedSULBandItem-ExtIEs} } OPTIONAL, 
	...
}

SupportedSULBandItem-ExtIEs XNAP-PROTOCOL-EXTENSION ::= {
	...
}


SymbolAllocation-in-Slot ::= CHOICE {
	allDL				SymbolAllocation-in-Slot-AllDL, 
	allUL				SymbolAllocation-in-Slot-AllUL, 
	bothDLandUL			SymbolAllocation-in-Slot-BothDLandUL, 
	choice-extension	ProtocolIE-Single-Container { {SymbolAllocation-in-Slot-ExtIEs} }
}

SymbolAllocation-in-Slot-ExtIEs XNAP-PROTOCOL-IES ::= {
	...
}


SymbolAllocation-in-Slot-AllDL ::= SEQUENCE {
	iE-Extension		ProtocolExtensionContainer { {SymbolAllocation-in-Slot-AllDL-ExtIEs} }	OPTIONAL, 
	...
}

SymbolAllocation-in-Slot-AllDL-ExtIEs XNAP-PROTOCOL-EXTENSION ::= {
	...
}


SymbolAllocation-in-Slot-AllUL ::= SEQUENCE {
	iE-Extension		ProtocolExtensionContainer { {SymbolAllocation-in-Slot-AllUL-ExtIEs} }	OPTIONAL, 
	...
}

SymbolAllocation-in-Slot-AllUL-ExtIEs XNAP-PROTOCOL-EXTENSION ::= {
	...
}


SymbolAllocation-in-Slot-BothDLandUL ::= SEQUENCE {
	numberofDLSymbols	INTEGER (0..13), 
	numberofULSymbols	INTEGER (0..13), 
	iE-Extension		ProtocolExtensionContainer { {SymbolAllocation-in-Slot-BothDLandUL-ExtIEs} }	OPTIONAL, 
	...
}

SymbolAllocation-in-Slot-BothDLandUL-ExtIEs XNAP-PROTOCOL-EXTENSION ::= {
	...
}


TABasedMDT ::= SEQUENCE {
	tAListforMDT		TAListforMDT, 
	iE-Extensions		ProtocolExtensionContainer { {TABasedMDT-ExtIEs} } OPTIONAL, 
	...
}

TABasedMDT-ExtIEs XNAP-PROTOCOL-EXTENSION ::= {
	...
}




TAIBasedMDT ::= SEQUENCE {
	tAIListforMDT			TAIListforMDT, 
	iE-Extensions			ProtocolExtensionContainer { {TAIBasedMDT-ExtIEs} } OPTIONAL, 
	...
}

TAIBasedMDT-ExtIEs XNAP-PROTOCOL-EXTENSION ::= {
	...
}

TAIListforMDT ::= SEQUENCE (SIZE(1..maxnoofTAforMDT)) OF TAIforMDT-Item

TAIforMDT-Item ::= SEQUENCE {
	plmn-ID				PLMN-Identity, 
	tAC						TAC, 
	iE-Extensions			ProtocolExtensionContainer { {TAIforMDT-Item-ExtIEs} } OPTIONAL, 
	...
}

TAIforMDT-Item-ExtIEs XNAP-PROTOCOL-EXTENSION ::= {
	...
}

TAC ::= OCTET STRING (SIZE (3))


TAISupport-List	::= SEQUENCE (SIZE(1..maxnoofsupportedTACs)) OF TAISupport-Item

TAISupport-Item ::= SEQUENCE {
	tac								TAC, 
	broadcastPLMNs					SEQUENCE (SIZE(1..maxnoofsupportedPLMNs)) OF BroadcastPLMNinTAISupport-Item, 
	iE-Extensions					ProtocolExtensionContainer { {TAISupport-Item-ExtIEs} } OPTIONAL, 
	...
}

TAISupport-Item-ExtIEs XNAP-PROTOCOL-EXTENSION ::= {
	...
}

TAListforMDT ::= SEQUENCE (SIZE(1..maxnoofTAforMDT)) OF TAC


TargetCellinEUTRAN  ::= OCTET STRING



Target-CGI ::= CHOICE {
	nr							NR-CGI, 
	e-utra						E-UTRA-CGI, 
	choice-extension			ProtocolIE-Single-Container { {TargetCGI-ExtIEs} }
}

TargetCGI-ExtIEs XNAP-PROTOCOL-IES ::= {
	...
}


TDDULDLConfigurationCommonNR ::= OCTET STRING


TargetCellList ::= SEQUENCE (SIZE(1..maxnoofCHOcells)) OF TargetCellList-Item

TargetCellList-Item ::= SEQUENCE {
	target-cell								NR-CGI, 
	iE-Extensions							ProtocolExtensionContainer { { TargetCellList-Item-ExtIEs} } OPTIONAL
}

TargetCellList-Item-ExtIEs XNAP-PROTOCOL-EXTENSION ::= {
	...
}

Threshold-RSRQ ::= INTEGER(0..34)
Threshold-RSRP ::= INTEGER(0..97)
Threshold-SINR ::= INTEGER(0..127)
TimeToTrigger ::= ENUMERATED {ms0,  ms40,  ms64,  ms80,  ms100,  ms128,  ms160,  ms256,  ms320,  ms480,  ms512,  ms640,  ms1024,  ms1280,  ms2560,  ms5120}


TimeToWait ::= ENUMERATED {
	v1s, 
	v2s, 
	v5s, 
	v10s, 
	v20s, 
	v60s, 
	...
}

TNLConfigurationInfo ::= SEQUENCE {
	extendedUPTransportLayerAddressesToAdd			ExtTLAs										OPTIONAL, 
	extendedUPTransportLayerAddressesToRemove		ExtTLAs										OPTIONAL, 
	iE-Extensions		ProtocolExtensionContainer { {TNLConfigurationInfo-ExtIEs} }	OPTIONAL, 
	...
}

TNLConfigurationInfo-ExtIEs XNAP-PROTOCOL-EXTENSION ::= {
	...
}

TNLA-To-Add-List ::= SEQUENCE (SIZE(1..maxnoofTNLAssociations)) OF TNLA-To-Add-Item

TNLA-To-Add-Item ::= SEQUENCE {
	tNLAssociationTransportLayerAddress		CPTransportLayerInformation, 
	tNLAssociationUsage						TNLAssociationUsage, 
	iE-Extensions							ProtocolExtensionContainer { { TNLA-To-Add-Item-ExtIEs} } OPTIONAL
}

TNLA-To-Add-Item-ExtIEs XNAP-PROTOCOL-EXTENSION ::= {
	...
}


TNLA-To-Update-List ::= SEQUENCE (SIZE(1..maxnoofTNLAssociations)) OF TNLA-To-Update-Item

TNLA-To-Update-Item::= SEQUENCE {
	tNLAssociationTransportLayerAddress		CPTransportLayerInformation, 
	tNLAssociationUsage						TNLAssociationUsage 	OPTIONAL, 
	iE-Extensions							ProtocolExtensionContainer { { TNLA-To-Update-Item-ExtIEs} } OPTIONAL
}

TNLA-To-Update-Item-ExtIEs XNAP-PROTOCOL-EXTENSION ::= {
	...
}

TNLA-To-Remove-List ::= SEQUENCE (SIZE(1..maxnoofTNLAssociations)) OF TNLA-To-Remove-Item

TNLA-To-Remove-Item::= SEQUENCE {
	tNLAssociationTransportLayerAddress		CPTransportLayerInformation, 
	iE-Extensions							ProtocolExtensionContainer { { TNLA-To-Remove-Item-ExtIEs} } OPTIONAL
}

TNLA-To-Remove-Item-ExtIEs XNAP-PROTOCOL-EXTENSION ::= {
	...
}


TNLA-Setup-List ::= SEQUENCE (SIZE(1..maxnoofTNLAssociations)) OF TNLA-Setup-Item

TNLA-Setup-Item ::= SEQUENCE {
	tNLAssociationTransportLayerAddress		CPTransportLayerInformation, 
	iE-Extensions							ProtocolExtensionContainer { { TNLA-Setup-Item-ExtIEs} } OPTIONAL, 
	...
}

TNLA-Setup-Item-ExtIEs XNAP-PROTOCOL-EXTENSION ::= {
	...
}


TNLA-Failed-To-Setup-List ::= SEQUENCE (SIZE(1..maxnoofTNLAssociations)) OF TNLA-Failed-To-Setup-Item

TNLA-Failed-To-Setup-Item ::= SEQUENCE {
	tNLAssociationTransportLayerAddress		CPTransportLayerInformation, 
	cause									Cause, 
	iE-Extensions							ProtocolExtensionContainer { { TNLA-Failed-To-Setup-Item-ExtIEs} } OPTIONAL
}

TNLA-Failed-To-Setup-Item-ExtIEs XNAP-PROTOCOL-EXTENSION ::= {
	...
}


TNLAssociationUsage ::= ENUMERATED {
	ue, 
	non-ue, 
	both,  
	...
}


TransportLayerAddress ::= BIT STRING (SIZE(1..160,  ...))


TraceActivation ::= SEQUENCE {
	ng-ran-TraceID			NG-RANTraceID, 
	interfaces-to-trace 	BIT STRING { ng-c (0),  x-nc (1),  uu (2),  f1-c (3),  e1 (4)} (SIZE(8)), 
	trace-depth 			Trace-Depth, 
	trace-coll-address		TransportLayerAddress, 
	ie-Extension 			ProtocolExtensionContainer { {TraceActivation-ExtIEs} } OPTIONAL, 
	...
}

TraceActivation-ExtIEs XNAP-PROTOCOL-EXTENSION ::= {

	{ ID id-TraceCollectionEntityURI	CRITICALITY ignore	EXTENSION URIaddress				PRESENCE optional}|
	{ ID id-MDT-Configuration			CRITICALITY ignore	EXTENSION MDT-Configuration			PRESENCE optional}, 
	...
}


Trace-Depth ::= ENUMERATED {
	minimum, 
	medium, 
	maximum, 
	minimumWithoutVendorSpecificExtension, 
	mediumWithoutVendorSpecificExtension, 
	maximumWithoutVendorSpecificExtension, 
	...
}


TSCTrafficCharacteristics ::= SEQUENCE {
	tSCAssistanceInformationDownlink	TSCAssistanceInformation OPTIONAL, 
	tSCAssistanceInformationUplink		TSCAssistanceInformation OPTIONAL, 
	ie-Extension 			ProtocolExtensionContainer { {TSCTrafficCharacteristics-ExtIEs} } OPTIONAL, 
	...
}

TSCTrafficCharacteristics-ExtIEs XNAP-PROTOCOL-EXTENSION ::= {
	...
}

TSCAssistanceInformation ::= SEQUENCE {
	periodicity			INTEGER (0.. 640000,  ...), 
	burstArrivalTime	OCTET STRING				OPTIONAL, 
	ie-Extension 			ProtocolExtensionContainer { { TSCAssistanceInformation-ExtIEs} } OPTIONAL, 
	...	
}

TSCAssistanceInformation-ExtIEs XNAP-PROTOCOL-EXTENSION ::= {
	...
}


TypeOfError ::= ENUMERATED {
	not-understood, 
	missing, 
	...
}



UEAggregateMaximumBitRate ::= SEQUENCE {
	dl-UE-AMBR				BitRate, 
	ul-UE-AMBR				BitRate, 
	iE-Extension			ProtocolExtensionContainer { {UEAggregateMaximumBitRate-ExtIEs} } OPTIONAL, 
	...
}

UEAggregateMaximumBitRate-ExtIEs XNAP-PROTOCOL-EXTENSION ::= {
	...
}


UEContextKeptIndicator ::= ENUMERATED {true,  ...}


UEContextID ::= CHOICE {
	rRCResume				UEContextIDforRRCResume, 
	rRRCReestablishment		UEContextIDforRRCReestablishment, 
	choice-extension		ProtocolIE-Single-Container { {UEContextID-ExtIEs} }
}

UEContextID-ExtIEs XNAP-PROTOCOL-IES ::= {
	...
}


UEContextIDforRRCResume ::= SEQUENCE {
	i-rnti					I-RNTI, 
	allocated-c-rnti			C-RNTI, 
	accessPCI				NG-RAN-CellPCI, 
	iE-Extension			ProtocolExtensionContainer { {UEContextIDforRRCResume-ExtIEs} } OPTIONAL, 
	...
}

UEContextIDforRRCResume-ExtIEs XNAP-PROTOCOL-EXTENSION ::= {
	...
}


UEContextIDforRRCReestablishment ::= SEQUENCE {
	c-rnti					C-RNTI, 
	failureCellPCI			NG-RAN-CellPCI, 
	iE-Extension			ProtocolExtensionContainer { {UEContextIDforRRCReestablishment-ExtIEs} } OPTIONAL, 
	...
}

UEContextIDforRRCReestablishment-ExtIEs XNAP-PROTOCOL-EXTENSION ::= {
	...
}


UEContextInfoRetrUECtxtResp ::= SEQUENCE {
	ng-c-UE-signalling-ref					AMF-UE-NGAP-ID, 
	signalling-TNL-at-source				CPTransportLayerInformation, 
	ueSecurityCapabilities					UESecurityCapabilities, 
	securityInformation						AS-SecurityInformation, 
	ue-AMBR									UEAggregateMaximumBitRate, 
	pduSessionResourcesToBeSetup-List		PDUSessionResourcesToBeSetup-List, 
	rrc-Context								OCTET STRING, 
	mobilityRestrictionList					MobilityRestrictionList									OPTIONAL, 
	indexToRatFrequencySelectionPriority	RFSP-Index												OPTIONAL, 
	iE-Extension			ProtocolExtensionContainer { {UEContextInfoRetrUECtxtResp-ExtIEs} } 	OPTIONAL, 
	...
}

UEContextInfoRetrUECtxtResp-ExtIEs XNAP-PROTOCOL-EXTENSION ::= {
	{ ID id-FiveGCMobilityRestrictionListContainer CRITICALITY ignore	EXTENSION FiveGCMobilityRestrictionListContainer		PRESENCE optional }|
{ ID id-NRUESidelinkAggregateMaximumBitRate	CRITICALITY ignore	EXTENSION NRUESidelinkAggregateMaximumBitRate	PRESENCE optional}|
{ ID id-LTEUESidelinkAggregateMaximumBitRate	CRITICALITY ignore	EXTENSION LTEUESidelinkAggregateMaximumBitRate	PRESENCE optional}|
	{ ID id-UERadioCapabilityID						CRITICALITY reject	EXTENSION UERadioCapabilityID								PRESENCE optional }, 
	...
}


UEHistoryInformation ::= SEQUENCE (SIZE(1..maxnoofCellsinUEHistoryInfo)) OF LastVisitedCell-Item


UEHistoryInformationFromTheUE ::= CHOICE {
	nR						NRMobilityHistoryReport, 
	choice-extension			ProtocolIE-Single-Container { {UEHistoryInformationFromTheUE-ExtIEs} }
}

UEHistoryInformationFromTheUE-ExtIEs XNAP-PROTOCOL-IES ::= {
	...
}


UEIdentityIndexValue ::= CHOICE {
	indexLength10				BIT STRING (SIZE(10)), 
	choice-extension			ProtocolIE-Single-Container { {UEIdentityIndexValue-ExtIEs} }
}

UEIdentityIndexValue-ExtIEs XNAP-PROTOCOL-IES ::= {
	...
}

UERadioCapabilityForPaging ::= SEQUENCE {
	uERadioCapabilityForPagingOfNR			UERadioCapabilityForPagingOfNR			OPTIONAL, 
	uERadioCapabilityForPagingOfEUTRA		UERadioCapabilityForPagingOfEUTRA		OPTIONAL, 
	iE-Extensions		ProtocolExtensionContainer { {UERadioCapabilityForPaging-ExtIEs} }	OPTIONAL, 
	...
}

UERadioCapabilityForPaging-ExtIEs XNAP-PROTOCOL-EXTENSION ::= {
	...
}

UERadioCapabilityForPagingOfNR ::= OCTET STRING

UERadioCapabilityForPagingOfEUTRA ::= OCTET STRING

UERadioCapabilityID ::= OCTET STRING 

UERANPagingIdentity ::= CHOICE {
	i-RNTI-full			BIT STRING ( SIZE (40)), 
	choice-extension	ProtocolIE-Single-Container { {UERANPagingIdentity-ExtIEs} }
}

UERANPagingIdentity-ExtIEs XNAP-PROTOCOL-IES ::= {
	...
}


UERLFReportContainer ::= CHOICE {
	nR-UERLFReportContainer			UERLFReportContainerNR, 
	lTE-UERLFReportContainer		UERLFReportContainerLTE, 
	choice-Extension		ProtocolIE-Single-Container { {UERLFReportContainer-ExtIEs} }
}
UERLFReportContainer-ExtIEs XNAP-PROTOCOL-IES ::= {
	...
}

UERLFReportContainerLTE ::= OCTET STRING


UERLFReportContainerNR ::= OCTET STRING



UESecurityCapabilities ::= SEQUENCE {
	nr-EncyptionAlgorithms					BIT STRING {nea1-128(1), 
														nea2-128(2), 
														nea3-128(3)} (SIZE(16,  ...)), 
	nr-IntegrityProtectionAlgorithms		BIT STRING {nia1-128(1), 
														nia2-128(2), 
														nia3-128(3)} (SIZE(16,  ...)), 
	e-utra-EncyptionAlgorithms				BIT STRING {eea1-128(1), 
														eea2-128(2), 
														eea3-128(3)} (SIZE(16,  ...)), 
	e-utra-IntegrityProtectionAlgorithms	BIT STRING {eia1-128(1), 
														eia2-128(2), 
														eia3-128(3)} (SIZE(16,  ...)), 
	iE-Extension			ProtocolExtensionContainer { {UESecurityCapabilities-ExtIEs} } OPTIONAL, 
	...
}

UESecurityCapabilities-ExtIEs XNAP-PROTOCOL-EXTENSION ::= {
	...
}


ULConfiguration::= SEQUENCE {
	uL-PDCP							UL-UE-Configuration, 
	iE-Extensions					ProtocolExtensionContainer { {ULConfiguration-ExtIEs} } OPTIONAL, 
	...
}

ULConfiguration-ExtIEs XNAP-PROTOCOL-EXTENSION ::= {
	...
}

UL-UE-Configuration::= ENUMERATED {no-data,  shared,  only,  ...}

ULForwarding	::= ENUMERATED {ul-forwarding-proposed,  ...}

ULForwardingProposal	::= ENUMERATED {ul-forwarding-proposed,  ...}


UL-GBR-PRB-usage::= INTEGER (0..100)


UL-non-GBR-PRB-usage::= INTEGER (0..100)


UL-Total-PRB-usage::= INTEGER (0..100)


UPTransportLayerInformation ::= CHOICE {
	gtpTunnel					GTPtunnelTransportLayerInformation, 
	choice-extension			ProtocolIE-Single-Container { {UPTransportLayerInformation-ExtIEs} }
}

UPTransportLayerInformation-ExtIEs XNAP-PROTOCOL-IES ::= {
	...
}


UPTransportParameters ::= SEQUENCE (SIZE(1..maxnoofSCellGroupsplus1)) OF UPTransportParametersItem

UPTransportParametersItem ::= SEQUENCE {
	upTNLInfo		UPTransportLayerInformation, 
	cellGroupID		CellGroupID, 
	iE-Extension	ProtocolExtensionContainer { {UPTransportParametersItem-ExtIEs} } OPTIONAL, 
	...
}

UPTransportParametersItem-ExtIEs XNAP-PROTOCOL-EXTENSION ::= {
	...
}


UserPlaneTrafficActivityReport ::= ENUMERATED {inactive,  re-activated,  ...}

URIaddress ::= VisibleString


VehicleUE ::= ENUMERATED { 
	authorized, 
	not-authorized, 
	...
}

VolumeTimedReportList ::= SEQUENCE (SIZE(1..maxnooftimeperiods)) OF VolumeTimedReport-Item

VolumeTimedReport-Item ::= SEQUENCE {
	startTimeStamp				OCTET STRING (SIZE(4)), 
	endTimeStamp					OCTET STRING (SIZE(4)), 
	usageCountUL					INTEGER (0..18446744073709551615), 
	usageCountDL					INTEGER (0..18446744073709551615), 
	iE-Extensions				ProtocolExtensionContainer { {VolumeTimedReport-Item-ExtIEs} } OPTIONAL, 
...
}

VolumeTimedReport-Item-ExtIEs XNAP-PROTOCOL-EXTENSION ::= {
	...
}


WLANMeasurementConfiguration ::= SEQUENCE {
	wlanMeasConfig             WLANMeasConfig, 
	wlanMeasConfigNameList		WLANMeasConfigNameList            OPTIONAL, 
	wlan-rssi                  ENUMERATED {true,  ...}            OPTIONAL, 
	wlan-rtt                   ENUMERATED {true,  ...}            OPTIONAL, 
	iE-Extensions		ProtocolExtensionContainer { { WLANMeasurementConfiguration-ExtIEs } } OPTIONAL, 
	...
}

WLANMeasurementConfiguration-ExtIEs XNAP-PROTOCOL-EXTENSION ::= {
	...
}

WLANMeasConfigNameList ::= SEQUENCE (SIZE(1..maxnoofWLANName)) OF WLANName

WLANMeasConfig::= ENUMERATED {setup, ...}

WLANName ::= OCTET STRING (SIZE (1..32))   


XnBenefitValue ::= INTEGER (1..8,  ...)




END






XnAP-CommonDataTypes {
itu-t (0) identified-organization (4) etsi (0) mobileDomain (0)
ngran-access (22) modules (3) xnap (2) version1 (1) xnap-CommonDataTypes (3) }

DEFINITIONS AUTOMATIC TAGS ::=

BEGIN






maxPrivateIEs 									INTEGER ::= 65535
maxProtocolExtensions 							INTEGER ::= 65535
maxProtocolIEs									INTEGER ::= 65535






Criticality		::= ENUMERATED { reject,  ignore,  notify }

Presence		::= ENUMERATED { optional,  conditional,  mandatory }

PrivateIE-ID	::= CHOICE {
	local				INTEGER (0.. maxPrivateIEs), 
	global				OBJECT IDENTIFIER
}

ProcedureCode		::= INTEGER (0..255)


ProtocolIE-ID		::= INTEGER (0..maxProtocolIEs)


TriggeringMessage	::= ENUMERATED { initiating-message,  successful-outcome,  unsuccessful-outcome}

END






XnAP-Constants {
itu-t (0) identified-organization (4) etsi (0) mobileDomain (0)
ngran-Access (22) modules (3) xnap (2) version1 (1) xnap-Constants (4) }

DEFINITIONS AUTOMATIC TAGS ::=

BEGIN

IMPORTS
	ProcedureCode, 
	ProtocolIE-ID
FROM XnAP-CommonDataTypes;






id-handoverPreparation											ProcedureCode ::= 0
id-sNStatusTransfer												ProcedureCode ::= 1
id-handoverCancel												ProcedureCode ::= 2
id-retrieveUEContext											ProcedureCode ::= 3
id-rANPaging													ProcedureCode ::= 4
id-xnUAddressIndication											ProcedureCode ::= 5
id-uEContextRelease												ProcedureCode ::= 6
id-sNGRANnodeAdditionPreparation								ProcedureCode ::= 7
id-sNGRANnodeReconfigurationCompletion							ProcedureCode ::= 8
id-mNGRANnodeinitiatedSNGRANnodeModificationPreparation			ProcedureCode ::= 9
id-sNGRANnodeinitiatedSNGRANnodeModificationPreparation			ProcedureCode ::= 10
id-mNGRANnodeinitiatedSNGRANnodeRelease							ProcedureCode ::= 11
id-sNGRANnodeinitiatedSNGRANnodeRelease							ProcedureCode ::= 12
id-sNGRANnodeCounterCheck										ProcedureCode ::= 13
id-sNGRANnodeChange												ProcedureCode ::= 14
id-rRCTransfer													ProcedureCode ::= 15
id-xnRemoval													ProcedureCode ::= 16
id-xnSetup														ProcedureCode ::= 17
id-nGRANnodeConfigurationUpdate									ProcedureCode ::= 18
id-cellActivation												ProcedureCode ::= 19
id-reset														ProcedureCode ::= 20
id-errorIndication												ProcedureCode ::= 21
id-privateMessage												ProcedureCode ::= 22
id-notificationControl											ProcedureCode ::= 23
id-activityNotification											ProcedureCode ::= 24
id-e-UTRA-NR-CellResourceCoordination							ProcedureCode ::= 25
id-secondaryRATDataUsageReport									ProcedureCode ::= 26
id-deactivateTrace												ProcedureCode ::= 27
id-traceStart													ProcedureCode ::= 28
id-handoverSuccess												ProcedureCode ::= 29
id-conditionalHandoverCancel									ProcedureCode ::= 30
id-earlyStatusTransfer										ProcedureCode ::= 31
id-failureIndication											ProcedureCode ::= 32
id-handoverReport											ProcedureCode ::= 33
id-resourceStatusReportingInitiation								ProcedureCode ::= 34
id-resourceStatusReporting										ProcedureCode ::= 35
id-mobilitySettingsChange										ProcedureCode ::= 36
id-accessAndMobilityIndication									ProcedureCode ::= 37






maxEARFCN									INTEGER ::= 262143
maxnoofAllowedAreas							INTEGER ::= 16
maxnoofAMFRegions							INTEGER ::= 16
maxnoofAoIs									INTEGER ::= 64
maxnoofBluetoothName						INTEGER ::= 4
maxnoofBPLMNs								INTEGER ::= 12
maxnoofCAGs									INTEGER ::= 12
maxnoofCAGsperPLMN							INTEGER ::= 256
maxnoofCellIDforMDT							INTEGER ::= 32
maxnoofCellsinAoI							INTEGER ::= 256
maxnoofCellsinUEHistoryInfo					INTEGER ::= 16
maxnoofCellsinNG-RANnode					INTEGER ::= 16384
maxnoofCellsinRNA							INTEGER ::= 32
maxnoofCellsUEMovingTrajectory				INTEGER ::= 16
maxnoofDRBs									INTEGER ::= 32
maxnoofEUTRABands							INTEGER ::= 16
maxnoofEUTRABPLMNs							INTEGER ::= 6
maxnoofEPLMNs								INTEGER ::= 15
maxnoofExtSliceItems						INTEGER ::= 65535
maxnoofEPLMNsplus1							INTEGER ::= 16
maxnoofForbiddenTACs							INTEGER ::= 4096
maxnoofFreqforMDT							INTEGER ::= 8
maxnoofMBSFNEUTRA							INTEGER ::= 8
maxnoofMDTPLMNs								INTEGER ::= 16
maxnoofMultiConnectivityMinusOne            INTEGER ::= 3
maxnoofNeighbours							INTEGER ::= 1024
maxnoofNeighPCIforMDT						INTEGER ::= 32
maxnoofNIDs									INTEGER ::= 12
maxnoofNRCellBands							INTEGER ::= 32
maxnoofPLMNs								INTEGER ::= 16
maxnoofPDUSessions							INTEGER ::= 256
maxnoofProtectedResourcePatterns			INTEGER ::= 16
maxnoofQoSFlows								INTEGER ::= 64
maxnoofQoSParaSets							INTEGER ::= 8
maxnoofRANAreaCodes							INTEGER ::= 32
maxnoofRANAreasinRNA						INTEGER ::= 16
maxnoofRANNodesinAoI						INTEGER ::= 64
maxnoofSCellGroups							INTEGER ::= 3
maxnoofSCellGroupsplus1						INTEGER ::= 4
maxnoofSensorName							INTEGER ::= 3
maxnoofSliceItems							INTEGER ::= 1024
maxnoofSNPNIDs								INTEGER ::= 12
maxnoofsupportedPLMNs						INTEGER ::= 12
maxnoofsupportedTACs						INTEGER ::= 256
maxnoofTAforMDT								INTEGER ::= 8
maxnoofTAI									INTEGER ::= 16
maxnoofTAIsinAoI 							INTEGER ::= 16
maxnooftimeperiods							INTEGER ::= 2
maxnoofTNLAssociations						INTEGER ::= 32
maxnoofUEContexts							INTEGER ::= 8192
maxNRARFCN									INTEGER ::= 3279165
maxNrOfErrors								INTEGER ::= 256
maxnoofslots								INTEGER ::= 5120
maxnoofExtTLAs								INTEGER ::= 16
maxnoofGTPTLAs								INTEGER ::= 16
maxnoofCHOcells								INTEGER ::= 8
maxnoofPC5QoSFlows 							INTEGER ::= 2064
maxnoofSSBAreas								INTEGER ::= 64
maxnoofRACHReports							INTEGER ::= 64
maxnoofNRSCSs								INTEGER ::= 5
maxnoofPhysicalResourceBlocks				INTEGER ::= 275
maxnoofAdditionalPDCPDuplicationTNL			INTEGER ::= 2
maxnoofRLCDuplicationstate		            INTEGER ::= 3
maxnoofWLANName								INTEGER ::= 4






id-ActivatedServedCells																				ProtocolIE-ID ::= 0
id-ActivationIDforCellActivation																	ProtocolIE-ID ::= 1
id-admittedSplitSRB																					ProtocolIE-ID ::= 2
id-admittedSplitSRBrelease																			ProtocolIE-ID ::= 3
id-AMF-Region-Information																			ProtocolIE-ID ::= 4
id-AssistanceDataForRANPaging																		ProtocolIE-ID ::= 5
id-BearersSubjectToCounterCheck																		ProtocolIE-ID ::= 6
id-Cause																							ProtocolIE-ID ::= 7
id-cellAssistanceInfo-NR																			ProtocolIE-ID ::= 8
id-ConfigurationUpdateInitiatingNodeChoice															ProtocolIE-ID ::= 9
id-CriticalityDiagnostics																			ProtocolIE-ID ::= 10
id-XnUAddressInfoperPDUSession-List																	ProtocolIE-ID ::= 11
id-DRBsSubjectToStatusTransfer-List																	ProtocolIE-ID ::= 12
id-ExpectedUEBehaviour																				ProtocolIE-ID ::= 13
id-GlobalNG-RAN-node-ID																				ProtocolIE-ID ::= 14
id-GUAMI																							ProtocolIE-ID ::= 15
id-indexToRatFrequSelectionPriority																	ProtocolIE-ID ::= 16
id-initiatingNodeType-ResourceCoordRequest															ProtocolIE-ID ::= 17
id-List-of-served-cells-E-UTRA																		ProtocolIE-ID ::= 18
id-List-of-served-cells-NR																			ProtocolIE-ID ::= 19
id-LocationReportingInformation																		ProtocolIE-ID ::= 20
id-MAC-I																							ProtocolIE-ID ::= 21
id-MaskedIMEISV																						ProtocolIE-ID ::= 22
id-M-NG-RANnodeUEXnAPID																				ProtocolIE-ID ::= 23
id-MN-to-SN-Container																				ProtocolIE-ID ::= 24
id-MobilityRestrictionList																			ProtocolIE-ID ::= 25
id-new-NG-RAN-Cell-Identity																			ProtocolIE-ID ::= 26
id-newNG-RANnodeUEXnAPID																			ProtocolIE-ID ::= 27
id-UEReportRRCTransfer																				ProtocolIE-ID ::= 28
id-oldNG-RANnodeUEXnAPID																			ProtocolIE-ID ::= 29
id-OldtoNewNG-RANnodeResumeContainer																ProtocolIE-ID ::= 30
id-PagingDRX																						ProtocolIE-ID ::= 31
id-PCellID																							ProtocolIE-ID ::= 32
id-PDCPChangeIndication																				ProtocolIE-ID ::= 33
id-PDUSessionAdmittedAddedAddReqAck																	ProtocolIE-ID ::= 34
id-PDUSessionAdmittedModSNModConfirm																ProtocolIE-ID ::= 35
id-PDUSessionAdmitted-SNModResponse																	ProtocolIE-ID ::= 36
id-PDUSessionNotAdmittedAddReqAck																	ProtocolIE-ID ::= 37
id-PDUSessionNotAdmitted-SNModResponse																ProtocolIE-ID ::= 38
id-PDUSessionReleasedList-RelConf																	ProtocolIE-ID ::= 39
id-PDUSessionReleasedSNModConfirm																	ProtocolIE-ID ::= 40
id-PDUSessionResourcesActivityNotifyList															ProtocolIE-ID ::= 41
id-PDUSessionResourcesAdmitted-List																	ProtocolIE-ID ::= 42
id-PDUSessionResourcesNotAdmitted-List																ProtocolIE-ID ::= 43
id-PDUSessionResourcesNotifyList																	ProtocolIE-ID ::= 44
id-PDUSession-SNChangeConfirm-List																	ProtocolIE-ID ::= 45
id-PDUSession-SNChangeRequired-List																	ProtocolIE-ID ::= 46
id-PDUSessionToBeAddedAddReq																		ProtocolIE-ID ::= 47
id-PDUSessionToBeModifiedSNModRequired																ProtocolIE-ID ::= 48
id-PDUSessionToBeReleasedList-RelRqd																ProtocolIE-ID ::= 49
id-PDUSessionToBeReleased-RelReq																	ProtocolIE-ID ::= 50
id-PDUSessionToBeReleasedSNModRequired																ProtocolIE-ID ::= 51
id-RANPagingArea																					ProtocolIE-ID ::= 52
id-PagingPriority																					ProtocolIE-ID ::= 53
id-requestedSplitSRB																				ProtocolIE-ID ::= 54
id-requestedSplitSRBrelease																			ProtocolIE-ID ::= 55
id-ResetRequestTypeInfo																				ProtocolIE-ID ::= 56
id-ResetResponseTypeInfo																			ProtocolIE-ID ::= 57
id-RespondingNodeTypeConfigUpdateAck																ProtocolIE-ID ::= 58
id-respondingNodeType-ResourceCoordResponse															ProtocolIE-ID ::= 59
id-ResponseInfo-ReconfCompl																			ProtocolIE-ID ::= 60
id-RRCConfigIndication																				ProtocolIE-ID ::= 61
id-RRCResumeCause																					ProtocolIE-ID ::= 62
id-SCGConfigurationQuery																			ProtocolIE-ID ::= 63
id-selectedPLMN																						ProtocolIE-ID ::= 64
id-ServedCellsToActivate																			ProtocolIE-ID ::= 65
id-servedCellsToUpdate-E-UTRA																		ProtocolIE-ID ::= 66
id-ServedCellsToUpdateInitiatingNodeChoice															ProtocolIE-ID ::= 67
id-servedCellsToUpdate-NR																			ProtocolIE-ID ::= 68
id-s-ng-RANnode-SecurityKey																			ProtocolIE-ID ::= 69
id-S-NG-RANnodeUE-AMBR																				ProtocolIE-ID ::= 70
id-S-NG-RANnodeUEXnAPID																				ProtocolIE-ID ::= 71
id-SN-to-MN-Container																				ProtocolIE-ID ::= 72
id-sourceNG-RANnodeUEXnAPID																			ProtocolIE-ID ::= 73
id-SplitSRB-RRCTransfer																				ProtocolIE-ID ::= 74
id-TAISupport-list																					ProtocolIE-ID ::= 75
id-TimeToWait																						ProtocolIE-ID ::= 76
id-Target2SourceNG-RANnodeTranspContainer															ProtocolIE-ID ::= 77
id-targetCellGlobalID																				ProtocolIE-ID ::= 78
id-targetNG-RANnodeUEXnAPID																			ProtocolIE-ID ::= 79
id-target-S-NG-RANnodeID																			ProtocolIE-ID ::= 80
id-TraceActivation																					ProtocolIE-ID ::= 81
id-UEContextID																						ProtocolIE-ID ::= 82
id-UEContextInfoHORequest																			ProtocolIE-ID ::= 83
id-UEContextInfoRetrUECtxtResp																		ProtocolIE-ID ::= 84
id-UEContextInfo-SNModRequest																		ProtocolIE-ID ::= 85
id-UEContextKeptIndicator																			ProtocolIE-ID ::= 86
id-UEContextRefAtSN-HORequest																		ProtocolIE-ID ::= 87
id-UEHistoryInformation																				ProtocolIE-ID ::= 88
id-UEIdentityIndexValue																				ProtocolIE-ID ::= 89
id-UERANPagingIdentity																				ProtocolIE-ID ::= 90
id-UESecurityCapabilities																			ProtocolIE-ID ::= 91
id-UserPlaneTrafficActivityReport																	ProtocolIE-ID ::= 92
id-XnRemovalThreshold 																				ProtocolIE-ID ::= 93
id-DesiredActNotificationLevel																		ProtocolIE-ID ::= 94
id-AvailableDRBIDs 																					ProtocolIE-ID ::= 95
id-AdditionalDRBIDs 																				ProtocolIE-ID ::= 96
id-SpareDRBIDs 																						ProtocolIE-ID ::= 97
id-RequiredNumberOfDRBIDs 																			ProtocolIE-ID ::= 98
id-TNLA-To-Add-List																					ProtocolIE-ID ::= 99
id-TNLA-To-Update-List																				ProtocolIE-ID ::= 100
id-TNLA-To-Remove-List																				ProtocolIE-ID ::= 101
id-TNLA-Setup-List																					ProtocolIE-ID ::= 102
id-TNLA-Failed-To-Setup-List																		ProtocolIE-ID ::= 103
id-PDUSessionToBeReleased-RelReqAck																	ProtocolIE-ID ::= 104
id-S-NG-RANnodeMaxIPDataRate-UL																		ProtocolIE-ID ::= 105
id-PDUSessionResourceSecondaryRATUsageList															ProtocolIE-ID ::= 107
id-Additional-UL-NG-U-TNLatUPF-List																	ProtocolIE-ID ::= 108
id-SecondarydataForwardingInfoFromTarget-List														ProtocolIE-ID ::= 109
id-LocationInformationSNReporting																	ProtocolIE-ID ::= 110
id-LocationInformationSN																			ProtocolIE-ID ::= 111
id-LastE-UTRANPLMNIdentity																			ProtocolIE-ID ::= 112
id-S-NG-RANnodeMaxIPDataRate-DL																		ProtocolIE-ID ::= 113
id-MaxIPrate-DL																						ProtocolIE-ID ::= 114
id-SecurityResult																					ProtocolIE-ID ::= 115
id-S-NSSAI																							ProtocolIE-ID ::= 116
id-MR-DC-ResourceCoordinationInfo																	ProtocolIE-ID ::= 117
id-AMF-Region-Information-To-Add																	ProtocolIE-ID ::= 118
id-AMF-Region-Information-To-Delete																	ProtocolIE-ID ::= 119
id-OldQoSFlowMap-ULendmarkerexpected																ProtocolIE-ID ::= 120
id-RANPagingFailure																					ProtocolIE-ID ::= 121
id-UERadioCapabilityForPaging																		ProtocolIE-ID ::= 122
id-PDUSessionDataForwarding-SNModResponse															ProtocolIE-ID ::= 123
id-DRBsNotAdmittedSetupModifyList																	ProtocolIE-ID ::= 124
id-Secondary-MN-Xn-U-TNLInfoatM																		ProtocolIE-ID ::= 125
id-NE-DC-TDM-Pattern																				ProtocolIE-ID ::= 126
id-PDUSessionCommonNetworkInstance																	ProtocolIE-ID ::= 127
id-BPLMN-ID-Info-EUTRA																				ProtocolIE-ID ::= 128
id-BPLMN-ID-Info-NR																					ProtocolIE-ID ::= 129
id-InterfaceInstanceIndication																		ProtocolIE-ID ::= 130
id-S-NG-RANnode-Addition-Trigger-Ind																ProtocolIE-ID ::= 131
id-DefaultDRB-Allowed																				ProtocolIE-ID ::= 132
id-DRB-IDs-takenintouse																				ProtocolIE-ID ::= 133
id-SplitSessionIndicator																			ProtocolIE-ID ::= 134
id-CNTypeRestrictionsForEquivalent																	ProtocolIE-ID ::= 135
id-CNTypeRestrictionsForServing																		ProtocolIE-ID ::= 136
id-DRBs-transferred-to-MN																			ProtocolIE-ID ::= 137
id-ULForwardingProposal																				ProtocolIE-ID ::= 138
id-EndpointIPAddressAndPort 																		ProtocolIE-ID ::= 139
id-IntendedTDD-DL-ULConfiguration-NR																ProtocolIE-ID ::= 140
id-TNLConfigurationInfo																				ProtocolIE-ID ::= 141
id-PartialListIndicator-NR																			ProtocolIE-ID ::= 142
id-MessageOversizeNotification																		ProtocolIE-ID ::= 143
id-CellAndCapacityAssistanceInfo-NR																	ProtocolIE-ID ::= 144
id-NG-RANTraceID																					ProtocolIE-ID ::= 145
id-NonGBRResources-Offered																			ProtocolIE-ID ::= 146
id-FastMCGRecoveryRRCTransfer-SN-to-MN																ProtocolIE-ID ::= 147
id-RequestedFastMCGRecoveryViaSRB3																	ProtocolIE-ID ::= 148
id-AvailableFastMCGRecoveryViaSRB3																	ProtocolIE-ID ::= 149
id-RequestedFastMCGRecoveryViaSRB3Release															ProtocolIE-ID ::= 150
id-ReleaseFastMCGRecoveryViaSRB3															ProtocolIE-ID ::= 151
id-FastMCGRecoveryRRCTransfer-MN-to-SN																ProtocolIE-ID ::= 152
id-ExtendedRATRestrictionInformation																ProtocolIE-ID ::= 153
id-QoSMonitoringRequest																			ProtocolIE-ID ::= 154
id-FiveGCMobilityRestrictionListContainer															ProtocolIE-ID ::= 155
id-PartialListIndicator-EUTRA																		ProtocolIE-ID ::= 156
id-CellAndCapacityAssistanceInfo-EUTRA																ProtocolIE-ID ::= 157
id-CHOinformation-Req																				ProtocolIE-ID ::= 158
id-CHOinformation-Ack																				ProtocolIE-ID ::= 159
id-targetCellsToCancel																				ProtocolIE-ID ::= 160
id-requestedTargetCellGlobalID																		ProtocolIE-ID ::= 161
id-procedureStage																					ProtocolIE-ID ::= 162
id-DAPSRequestInfo																					ProtocolIE-ID ::= 163
id-DAPSResponseInfo-List																			ProtocolIE-ID ::= 164
id-CHO-MRDC-Indicator																				ProtocolIE-ID ::= 165
id-OffsetOfNbiotChannelNumberToDL-EARFCN																ProtocolIE-ID ::= 166
id-OffsetOfNbiotChannelNumberToUL-EARFCN																ProtocolIE-ID ::= 167
id-NBIoT-UL-DL-AlignmentOffset																		ProtocolIE-ID ::= 168
id-LTEV2XServicesAuthorized																			ProtocolIE-ID ::= 169
id-NRV2XServicesAuthorized																			ProtocolIE-ID ::= 170
id-LTEUESidelinkAggregateMaximumBitRate																ProtocolIE-ID ::= 171
id-NRUESidelinkAggregateMaximumBitRate																ProtocolIE-ID ::= 172
id-PC5QoSParameters																					ProtocolIE-ID ::= 173
id-AlternativeQoSParaSetList																			ProtocolIE-ID ::= 174
id-CurrentQoSParaSetIndex																			ProtocolIE-ID ::= 175
id-MobilityInformation 																				ProtocolIE-ID ::= 176
id-InitiatingCondition-FailureIndication															ProtocolIE-ID ::= 177  
id-UEHistoryInformationFromTheUE																		ProtocolIE-ID ::= 178 
id-HandoverReportType																				ProtocolIE-ID ::= 179 
id-HandoverCause																					ProtocolIE-ID ::= 180 
id-SourceCellCGI																					ProtocolIE-ID ::= 181 
id-TargetCellCGI																					ProtocolIE-ID ::= 182 
id-ReEstablishmentCellCGI																			ProtocolIE-ID ::= 183 
id-TargetCellinEUTRAN																				ProtocolIE-ID ::= 184 
id-SourceCellCRNTI																					ProtocolIE-ID ::= 185 
id-UERLFReportContainer																				ProtocolIE-ID ::= 186 
id-NGRAN-Node1-Measurement-ID																		ProtocolIE-ID ::= 187 
id-NGRAN-Node2-Measurement-ID																		ProtocolIE-ID ::= 188 
id-RegistrationRequest																				ProtocolIE-ID ::= 189 
id-ReportCharacteristics																					ProtocolIE-ID ::= 190 
id-CellToReport																								ProtocolIE-ID ::= 191 
id-ReportingPeriodicity																					ProtocolIE-ID ::= 192 
id-CellMeasurementResult																					ProtocolIE-ID ::= 193 
id-NG-RANnode1CellID																						ProtocolIE-ID ::= 194 
id-NG-RANnode2CellID																				ProtocolIE-ID ::= 195 
id-NG-RANnode1MobilityParameters																		ProtocolIE-ID ::= 196 
id-NG-RANnode2ProposedMobilityParameters																ProtocolIE-ID ::= 197 
id-MobilityParametersModificationRange																ProtocolIE-ID ::= 198 
id-TDDULDLConfigurationCommonNR																		ProtocolIE-ID ::= 199
id-CarrierList																						ProtocolIE-ID ::= 200
id-ULCarrierList																					ProtocolIE-ID ::= 201
id-FrequencyShift7p5khz																				ProtocolIE-ID ::= 202
id-SSB-PositionsInBurst																				ProtocolIE-ID ::= 203
id-NRCellPRACHConfig																				ProtocolIE-ID ::= 204
id-RACHReportInformation																				ProtocolIE-ID ::= 205 
id-IABNodeIndication																				ProtocolIE-ID ::= 206
id-Redundant-UL-NG-U-TNLatUPF																		ProtocolIE-ID ::= 207
id-CNPacketDelayBudgetDownlink																		ProtocolIE-ID ::= 208
id-CNPacketDelayBudgetUplink																			ProtocolIE-ID ::= 209
id-Additional-Redundant-UL-NG-U-TNLatUPF-List														ProtocolIE-ID ::= 210
id-RedundantCommonNetworkInstance																	ProtocolIE-ID ::= 211
id-TSCTrafficCharacteristics																			ProtocolIE-ID ::= 212
id-RedundantQoSFlowIndicator																			ProtocolIE-ID ::= 213
id-Redundant-DL-NG-U-TNLatNG-RAN																		ProtocolIE-ID ::= 214
id-ExtendedPacketDelayBudget																			ProtocolIE-ID ::= 215
id-Additional-PDCP-Duplication-TNL-List																ProtocolIE-ID ::= 216
id-RedundantPDUSessionInformation																	ProtocolIE-ID ::= 217
id-UsedRSNInformation																				ProtocolIE-ID ::= 218
id-RLCDuplicationInformation																			ProtocolIE-ID ::= 219
id-NPN-Broadcast-Information																			ProtocolIE-ID ::= 220
id-NPNPagingAssistanceInformation																	ProtocolIE-ID ::= 221
id-NPNMobilityInformation																			ProtocolIE-ID ::= 222
id-NPN-Support																						ProtocolIE-ID ::= 223
id-MDT-Configuration																				ProtocolIE-ID ::= 224
id-MDTPLMNList																						ProtocolIE-ID ::= 225
id-TraceCollectionEntityURI																			ProtocolIE-ID ::= 226
id-UERadioCapabilityID																				ProtocolIE-ID ::= 227
id-CSI-RSTransmissionIndication																		ProtocolIE-ID ::= 228
id-SNTriggered  																					ProtocolIE-ID ::= 229
id-DLCarrierList																					ProtocolIE-ID ::= 230
id-ExtendedTAISliceSupportList																		ProtocolIE-ID ::= 231
id-cellAssistanceInfo-EUTRA																			ProtocolIE-ID ::= 232


END






XnAP-Containers {
itu-t (0) identified-organization (4) etsi (0) mobileDomain (0)
ngran-access (22) modules (3) xnap (2) version1 (1) xnap-Containers (5) }

DEFINITIONS AUTOMATIC TAGS ::=

BEGIN






IMPORTS
	maxPrivateIEs, 
	maxProtocolExtensions, 
	maxProtocolIEs, 
	Criticality, 
	Presence, 
	PrivateIE-ID, 
	ProtocolIE-ID	
FROM XnAP-CommonDataTypes;






XNAP-PROTOCOL-IES ::= CLASS {
	&id				ProtocolIE-ID 			UNIQUE, 
	&criticality	Criticality, 
	&Value, 
	&presence		Presence
}
WITH SYNTAX {
	ID				&id
	CRITICALITY		&criticality
	TYPE			&Value
	PRESENCE		&presence
}






XNAP-PROTOCOL-IES-PAIR ::= CLASS {
	&id						ProtocolIE-ID 		UNIQUE, 
	&firstCriticality		Criticality, 
	&FirstValue, 
	&secondCriticality		Criticality, 
	&SecondValue, 
	&presence				Presence
}
WITH SYNTAX {
	ID						&id
	FIRST CRITICALITY 		&firstCriticality
	FIRST TYPE				&FirstValue
	SECOND CRITICALITY 		&secondCriticality
	SECOND TYPE				&SecondValue
	PRESENCE				&presence
}






XNAP-PROTOCOL-EXTENSION ::= CLASS {
	&id					ProtocolIE-ID 		UNIQUE, 
	&criticality		Criticality, 
	&Extension, 
	&presence			Presence
}
WITH SYNTAX {
	ID					&id
	CRITICALITY			&criticality
	EXTENSION			&Extension
	PRESENCE			&presence
}






XNAP-PRIVATE-IES ::= CLASS {
	&id					PrivateIE-ID, 
	&criticality		Criticality, 
	&Value, 
	&presence			Presence
}
WITH SYNTAX {
	ID					&id
	CRITICALITY			&criticality
	TYPE				&Value
	PRESENCE			&presence
}






ProtocolIE-Container {XNAP-PROTOCOL-IES : IEsSetParam} ::=
	SEQUENCE (SIZE (0..maxProtocolIEs)) OF
	ProtocolIE-Field {{IEsSetParam}}

ProtocolIE-Single-Container {XNAP-PROTOCOL-IES : IEsSetParam} ::= 	ProtocolIE-Field {{IEsSetParam}}

ProtocolIE-Field {XNAP-PROTOCOL-IES : IEsSetParam} ::= SEQUENCE {
	id				XNAP-PROTOCOL-IES.&id					({IEsSetParam}), 
	criticality		XNAP-PROTOCOL-IES.&criticality			({IEsSetParam}{@id}), 
	value			XNAP-PROTOCOL-IES.&Value				({IEsSetParam}{@id})
}






ProtocolIE-ContainerPair {XNAP-PROTOCOL-IES-PAIR : IEsSetParam} ::=
	SEQUENCE (SIZE (0..maxProtocolIEs)) OF
	ProtocolIE-FieldPair {{IEsSetParam}}

ProtocolIE-FieldPair {XNAP-PROTOCOL-IES-PAIR : IEsSetParam} ::= SEQUENCE {
	id					XNAP-PROTOCOL-IES-PAIR.&id					({IEsSetParam}), 
	firstCriticality	XNAP-PROTOCOL-IES-PAIR.&firstCriticality	({IEsSetParam}{@id}), 
	firstValue			XNAP-PROTOCOL-IES-PAIR.&FirstValue			({IEsSetParam}{@id}), 
	secondCriticality	XNAP-PROTOCOL-IES-PAIR.&secondCriticality	({IEsSetParam}{@id}), 
	secondValue			XNAP-PROTOCOL-IES-PAIR.&SecondValue			({IEsSetParam}{@id})
}






ProtocolIE-ContainerList {INTEGER : lowerBound,  INTEGER : upperBound,  XNAP-PROTOCOL-IES : IEsSetParam} ::=
	SEQUENCE (SIZE (lowerBound..upperBound)) OF
	ProtocolIE-Container {{IEsSetParam}}

ProtocolIE-ContainerPairList {INTEGER : lowerBound,  INTEGER : upperBound,  XNAP-PROTOCOL-IES-PAIR : IEsSetParam} ::=
	SEQUENCE (SIZE (lowerBound..upperBound)) OF
	ProtocolIE-ContainerPair {{IEsSetParam}}






ProtocolExtensionContainer {XNAP-PROTOCOL-EXTENSION : ExtensionSetParam} ::=	SEQUENCE (SIZE (1..maxProtocolExtensions)) OF
	ProtocolExtensionField {{ExtensionSetParam}}

ProtocolExtensionField {XNAP-PROTOCOL-EXTENSION : ExtensionSetParam} ::= SEQUENCE {
	id					XNAP-PROTOCOL-EXTENSION.&id				({ExtensionSetParam}), 
	criticality			XNAP-PROTOCOL-EXTENSION.&criticality	({ExtensionSetParam}{@id}), 
	extensionValue		XNAP-PROTOCOL-EXTENSION.&Extension		({ExtensionSetParam}{@id})
}






PrivateIE-Container {XNAP-PRIVATE-IES : IEsSetParam} ::=
	SEQUENCE (SIZE (1..maxPrivateIEs)) OF
	PrivateIE-Field {{IEsSetParam}}

PrivateIE-Field {XNAP-PRIVATE-IES : IEsSetParam} ::= SEQUENCE {
	id				XNAP-PRIVATE-IES.&id			({IEsSetParam}), 
	criticality		XNAP-PRIVATE-IES.&criticality	({IEsSetParam}{@id}), 
	value			XNAP-PRIVATE-IES.&Value			({IEsSetParam}{@id})
}

END
