NRPPA-PDU-Descriptions {
itu-t (0) identified-organization (4) etsi (0) mobileDomain (0)
ngran-access (22) modules (3) nrppa (4) version1 (1) nrppa-PDU-Descriptions (0) }

DEFINITIONS AUTOMATIC TAGS ::= 

BEGIN





IMPORTS
	Criticality, 
	ProcedureCode, 
	NRPPATransactionID

FROM NRPPA-CommonDataTypes


	ErrorIndication, 
	PrivateMessage, 
	E-CIDMeasurementInitiationRequest, 
	E-CIDMeasurementInitiationResponse, 
	E-CIDMeasurementInitiationFailure, 
	E-CIDMeasurementFailureIndication, 
	E-CIDMeasurementReport, 
	E-CIDMeasurementTerminationCommand, 
	OTDOAInformationRequest, 
	OTDOAInformationResponse, 
	OTDOAInformationFailure


FROM NRPPA-PDU-Contents

	id-errorIndication, 
	id-privateMessage, 
	id-e-CIDMeasurementInitiation, 
	id-e-CIDMeasurementFailureIndication, 
	id-e-CIDMeasurementReport, 
	id-e-CIDMeasurementTermination, 
	id-oTDOAInformationExchange


FROM NRPPA-Constants;





NRPPA-ELEMENTARY-PROCEDURE ::= CLASS {
	&InitiatingMessage				, 
	&SuccessfulOutcome							OPTIONAL, 
	&UnsuccessfulOutcome						OPTIONAL, 
	&procedureCode				ProcedureCode	UNIQUE, 
	&criticality				Criticality	DEFAULT ignore
}
WITH SYNTAX {
	INITIATING MESSAGE			&InitiatingMessage
	[SUCCESSFUL OUTCOME		&SuccessfulOutcome]
	[UNSUCCESSFUL OUTCOME		&UnsuccessfulOutcome]
	PROCEDURE CODE				&procedureCode
	[CRITICALITY				&criticality]
}





NRPPA-PDU ::= CHOICE {
	initiatingMessage		InitiatingMessage, 
	successfulOutcome		SuccessfulOutcome, 
	unsuccessfulOutcome	UnsuccessfulOutcome, 
	...
}

InitiatingMessage ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&InitiatingMessage	({NRPPA-ELEMENTARY-PROCEDURES}{@procedureCode})
}

SuccessfulOutcome ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&SuccessfulOutcome	({NRPPA-ELEMENTARY-PROCEDURES}{@procedureCode})
}

UnsuccessfulOutcome ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&UnsuccessfulOutcome	({NRPPA-ELEMENTARY-PROCEDURES}{@procedureCode})
}





NRPPA-ELEMENTARY-PROCEDURES NRPPA-ELEMENTARY-PROCEDURE ::= {
	NRPPA-ELEMENTARY-PROCEDURES-CLASS-1			|
	NRPPA-ELEMENTARY-PROCEDURES-CLASS-2			, 
	...
}

NRPPA-ELEMENTARY-PROCEDURES-CLASS-1 NRPPA-ELEMENTARY-PROCEDURE ::= {
	e-CIDMeasurementInitiation	|
	oTDOAInformationExchange		, 
	...
}

NRPPA-ELEMENTARY-PROCEDURES-CLASS-2 NRPPA-ELEMENTARY-PROCEDURE ::= {
	e-CIDMeasurementFailureIndication		|
	e-CIDMeasurementReport					|
	e-CIDMeasurementTermination				|
	errorIndication						|
	privateMessage							, 
	...
}





e-CIDMeasurementInitiation NRPPA-ELEMENTARY-PROCEDURE ::= {
	INITIATING MESSAGE		E-CIDMeasurementInitiationRequest
	SUCCESSFUL OUTCOME		E-CIDMeasurementInitiationResponse
	UNSUCCESSFUL OUTCOME	E-CIDMeasurementInitiationFailure
	PROCEDURE CODE			id-e-CIDMeasurementInitiation
	CRITICALITY				reject
}

e-CIDMeasurementFailureIndication NRPPA-ELEMENTARY-PROCEDURE ::= {
	INITIATING MESSAGE		E-CIDMeasurementFailureIndication
	PROCEDURE CODE			id-e-CIDMeasurementFailureIndication
	CRITICALITY				ignore
}

e-CIDMeasurementReport NRPPA-ELEMENTARY-PROCEDURE ::= {
	INITIATING MESSAGE		E-CIDMeasurementReport
	PROCEDURE CODE			id-e-CIDMeasurementReport
	CRITICALITY				ignore
}

e-CIDMeasurementTermination NRPPA-ELEMENTARY-PROCEDURE ::= {
	INITIATING MESSAGE		E-CIDMeasurementTerminationCommand
	PROCEDURE CODE			id-e-CIDMeasurementTermination
	CRITICALITY				reject
}

oTDOAInformationExchange NRPPA-ELEMENTARY-PROCEDURE ::= {
	INITIATING MESSAGE		OTDOAInformationRequest
	SUCCESSFUL OUTCOME		OTDOAInformationResponse
	UNSUCCESSFUL OUTCOME	OTDOAInformationFailure
	PROCEDURE CODE			id-oTDOAInformationExchange
	CRITICALITY				reject
}

errorIndication NRPPA-ELEMENTARY-PROCEDURE ::= {
	INITIATING MESSAGE		ErrorIndication
	PROCEDURE CODE			id-errorIndication
	CRITICALITY			ignore
}


privateMessage			NRPPA-ELEMENTARY-PROCEDURE ::= {
	INITIATING MESSAGE		PrivateMessage
	PROCEDURE CODE			id-privateMessage
	CRITICALITY			ignore
}

END





NRPPA-PDU-Contents {
itu-t (0) identified-organization (4) etsi (0) mobileDomain (0) 
ngran-access (22) modules (3) nrppa (4) version1 (1) nrppa-PDU-Contents (1) }

DEFINITIONS AUTOMATIC TAGS ::= 

BEGIN





IMPORTS
	
	Cause, 
	CriticalityDiagnostics, 
	E-CID-MeasurementResult, 
	OTDOACells, 
	OTDOA-Information-Item, 
	Measurement-ID, 
	MeasurementPeriodicity, 
	MeasurementQuantities, 
	ReportCharacteristics, 
	RequestedSRSTransmissionCharacteristics, 
	Cell-Portion-ID, 
	OtherRATMeasurementQuantities, 
	OtherRATMeasurementResult, 
	WLANMeasurementQuantities, 
	WLANMeasurementResult
	
FROM NRPPA-IEs

	PrivateIE-Container{}, 
	ProtocolExtensionContainer{}, 
	ProtocolIE-Container{}, 
	ProtocolIE-ContainerList{}, 
	ProtocolIE-Single-Container{}, 
	NRPPA-PRIVATE-IES, 
	NRPPA-PROTOCOL-EXTENSION, 
	NRPPA-PROTOCOL-IES
FROM NRPPA-Containers

	
	maxnoOTDOAtypes, 
	id-Cause, 
	id-CriticalityDiagnostics, 
	id-LMF-UE-Measurement-ID, 
	id-OTDOACells, 
	id-OTDOA-Information-Type-Group, 
	id-OTDOA-Information-Type-Item, 
	id-ReportCharacteristics, 
	id-MeasurementPeriodicity, 
	id-MeasurementQuantities, 
	id-RAN-UE-Measurement-ID, 
	id-E-CID-MeasurementResult, 
	id-RequestedSRSTransmissionCharacteristics, 
	id-Cell-Portion-ID, 
	id-OtherRATMeasurementQuantities, 
	id-OtherRATMeasurementResult, 
	id-WLANMeasurementQuantities, 
	id-WLANMeasurementResult
	
FROM NRPPA-Constants;





E-CIDMeasurementInitiationRequest ::= SEQUENCE {
	protocolIEs		ProtocolIE-Container	{{E-CIDMeasurementInitiationRequest-IEs}}, 
	...
}

E-CIDMeasurementInitiationRequest-IEs NRPPA-PROTOCOL-IES ::= {
	{ ID id-LMF-UE-Measurement-ID			CRITICALITY reject	TYPE Measurement-ID						PRESENCE mandatory}|
	{ ID id-ReportCharacteristics			CRITICALITY reject	TYPE ReportCharacteristics				PRESENCE mandatory}|
	{ ID id-MeasurementPeriodicity			CRITICALITY reject	TYPE MeasurementPeriodicity				PRESENCE conditional}|

	{ ID id-MeasurementQuantities			CRITICALITY reject	TYPE MeasurementQuantities				PRESENCE mandatory}|
	{ ID id-OtherRATMeasurementQuantities	CRITICALITY ignore	TYPE OtherRATMeasurementQuantities	PRESENCE optional}|
	{ ID id-WLANMeasurementQuantities		CRITICALITY ignore	TYPE WLANMeasurementQuantities			PRESENCE optional}, 
	...
}





E-CIDMeasurementInitiationResponse ::= SEQUENCE {
	protocolIEs		ProtocolIE-Container	{{E-CIDMeasurementInitiationResponse-IEs}}, 
	...
}

E-CIDMeasurementInitiationResponse-IEs NRPPA-PROTOCOL-IES ::= {
	{ ID id-LMF-UE-Measurement-ID		CRITICALITY reject	TYPE Measurement-ID					PRESENCE mandatory}|
	{ ID id-RAN-UE-Measurement-ID		CRITICALITY reject	TYPE Measurement-ID					PRESENCE mandatory}|
	{ ID id-E-CID-MeasurementResult		CRITICALITY ignore	TYPE E-CID-MeasurementResult			PRESENCE optional}|
	{ ID id-CriticalityDiagnostics		CRITICALITY ignore	TYPE CriticalityDiagnostics			PRESENCE optional}|
	{ ID id-Cell-Portion-ID				CRITICALITY ignore	TYPE Cell-Portion-ID					PRESENCE optional}|
	{ ID id-OtherRATMeasurementResult	CRITICALITY ignore	TYPE OtherRATMeasurementResult		PRESENCE optional}|
	{ ID id-WLANMeasurementResult		CRITICALITY ignore	TYPE WLANMeasurementResult			PRESENCE optional}, 
	...
}





E-CIDMeasurementInitiationFailure ::= SEQUENCE {
	protocolIEs						ProtocolIE-Container		{{E-CIDMeasurementInitiationFailure-IEs}}, 
	...
}


E-CIDMeasurementInitiationFailure-IEs NRPPA-PROTOCOL-IES ::= {
	{ ID id-LMF-UE-Measurement-ID		CRITICALITY reject	TYPE Measurement-ID				PRESENCE mandatory}|
	{ ID id-Cause							CRITICALITY ignore	TYPE Cause							PRESENCE mandatory}|
	{ ID id-CriticalityDiagnostics		CRITICALITY ignore	TYPE CriticalityDiagnostics		PRESENCE optional}, 
	...
}





E-CIDMeasurementFailureIndication ::= SEQUENCE {
	protocolIEs						ProtocolIE-Container		{{E-CIDMeasurementFailureIndication-IEs}}, 
	...
}


E-CIDMeasurementFailureIndication-IEs NRPPA-PROTOCOL-IES ::= {
	{ ID id-LMF-UE-Measurement-ID		CRITICALITY reject	TYPE Measurement-ID				PRESENCE mandatory}|
	{ ID id-RAN-UE-Measurement-ID		CRITICALITY reject	TYPE Measurement-ID				PRESENCE mandatory}|
	{ ID id-Cause							CRITICALITY ignore	TYPE Cause							PRESENCE mandatory}, 
	...
}





E-CIDMeasurementReport ::= SEQUENCE {
	protocolIEs						ProtocolIE-Container		{{E-CIDMeasurementReport-IEs}}, 
	...
}


E-CIDMeasurementReport-IEs NRPPA-PROTOCOL-IES ::= {
	{ ID id-LMF-UE-Measurement-ID		CRITICALITY reject	TYPE Measurement-ID				PRESENCE mandatory}|
	{ ID id-RAN-UE-Measurement-ID		CRITICALITY reject	TYPE Measurement-ID				PRESENCE mandatory}|
	{ ID id-E-CID-MeasurementResult		CRITICALITY ignore	TYPE E-CID-MeasurementResult		PRESENCE mandatory}|
	{ ID id-Cell-Portion-ID				CRITICALITY ignore	TYPE Cell-Portion-ID				PRESENCE optional}, 
	...
}





E-CIDMeasurementTerminationCommand ::= SEQUENCE {
	protocolIEs						ProtocolIE-Container		{{E-CIDMeasurementTerminationCommand-IEs}}, 
	...
}


E-CIDMeasurementTerminationCommand-IEs NRPPA-PROTOCOL-IES ::= {
	{ ID id-LMF-UE-Measurement-ID		CRITICALITY reject	TYPE Measurement-ID				PRESENCE mandatory}|
	{ ID id-RAN-UE-Measurement-ID		CRITICALITY reject	TYPE Measurement-ID				PRESENCE mandatory}, 
	...
}





OTDOAInformationRequest ::= SEQUENCE {
	protocolIEs		ProtocolIE-Container	{{OTDOAInformationRequest-IEs}}, 
	...
}

OTDOAInformationRequest-IEs NRPPA-PROTOCOL-IES ::= {
	{ ID id-OTDOA-Information-Type-Group		CRITICALITY reject	TYPE OTDOA-Information-Type			PRESENCE mandatory}, 
	...
}

OTDOA-Information-Type ::= SEQUENCE (SIZE(1..maxnoOTDOAtypes)) OF ProtocolIE-Single-Container { { OTDOA-Information-TypeIEs} }

OTDOA-Information-TypeIEs	NRPPA-PROTOCOL-IES ::= {
	{ ID id-OTDOA-Information-Type-Item		CRITICALITY reject	TYPE OTDOA-Information-Type-Item	PRESENCE mandatory}, 
	...
}

OTDOA-Information-Type-Item ::= SEQUENCE {
	oTDOA-Information-Type-Item		OTDOA-Information-Item, 
	iE-Extensions					ProtocolExtensionContainer { { OTDOA-Information-Type-ItemExtIEs} } OPTIONAL, 
	...
}

OTDOA-Information-Type-ItemExtIEs NRPPA-PROTOCOL-EXTENSION ::= {
	...
}





OTDOAInformationResponse ::= SEQUENCE {
	protocolIEs		ProtocolIE-Container	{{OTDOAInformationResponse-IEs}}, 
	...
}

OTDOAInformationResponse-IEs NRPPA-PROTOCOL-IES ::= {
	{ ID id-OTDOACells						CRITICALITY ignore	TYPE OTDOACells					PRESENCE mandatory}|
	{ ID id-CriticalityDiagnostics			CRITICALITY ignore	TYPE CriticalityDiagnostics		PRESENCE optional}, 
	...
}





OTDOAInformationFailure ::= SEQUENCE {
	protocolIEs						ProtocolIE-Container		{{OTDOAInformationFailure-IEs}}, 
	...
}


OTDOAInformationFailure-IEs NRPPA-PROTOCOL-IES ::= {
	{ ID id-Cause							CRITICALITY ignore	TYPE Cause						PRESENCE mandatory}|
	{ ID id-CriticalityDiagnostics			CRITICALITY ignore	TYPE CriticalityDiagnostics		PRESENCE optional}, 
	...
}





ErrorIndication ::= SEQUENCE {
	protocolIEs		ProtocolIE-Container	{{ErrorIndication-IEs}}, 
	...
}

ErrorIndication-IEs NRPPA-PROTOCOL-IES ::= {
	
	{ ID id-Cause							CRITICALITY ignore	TYPE Cause						PRESENCE optional}|
	{ ID id-CriticalityDiagnostics		CRITICALITY ignore	TYPE CriticalityDiagnostics	PRESENCE optional}, 
	...
}





PrivateMessage ::= SEQUENCE {
	privateIEs		PrivateIE-Container	{{PrivateMessage-IEs}}, 
	...
}

PrivateMessage-IEs NRPPA-PRIVATE-IES ::= {
	...
}

END





NRPPA-IEs {
itu-t (0) identified-organization (4) etsi (0) mobileDomain (0) 
ngran-access (22) modules (3) nrppa (4) version1 (1) nrppa-IEs (2) }

DEFINITIONS AUTOMATIC TAGS ::= 

BEGIN

IMPORTS	
	
	id-MeasurementQuantities-Item, 
	maxCellinRANnode, 
	maxCellReport, 
	maxNrOfErrors, 
	maxNoMeas, 
	maxnoOTDOAtypes, 
	maxServCell, 
	id-OtherRATMeasurementQuantities-Item, 
	id-WLANMeasurementQuantities-Item, 
	maxGERANMeas, 
	maxUTRANMeas, 
	maxWLANchannels, 
	maxnoFreqHoppingBandsMinusOne


FROM NRPPA-Constants

	Criticality, 
	NRPPATransactionID, 
	ProcedureCode, 
	ProtocolIE-ID, 
	TriggeringMessage

FROM NRPPA-CommonDataTypes

	ProtocolExtensionContainer{}, 
	ProtocolIE-Single-Container{}, 
	
	NRPPA-PROTOCOL-EXTENSION, 
	NRPPA-PROTOCOL-IES

FROM NRPPA-Containers;


BCCH ::= INTEGER (0..1023,  ...)

BSSID ::= OCTET STRING (SIZE(6))

Cause ::= CHOICE {
	radioNetwork		CauseRadioNetwork, 
	protocol			CauseProtocol, 
	misc				CauseMisc, 
	...
}

CauseMisc ::= ENUMERATED {
	unspecified, 
	...
}

CauseProtocol ::= ENUMERATED {
	transfer-syntax-error, 
	abstract-syntax-error-reject, 
	abstract-syntax-error-ignore-and-notify, 
	message-not-compatible-with-receiver-state, 
	semantic-error, 
	unspecified, 
	abstract-syntax-error-falsely-constructed-message, 
	...
}

CauseRadioNetwork ::= ENUMERATED {
	unspecified, 
	requested-item-not-supported, 
	requested-item-temporarily-not-available, 
	...

}

Cell-Portion-ID ::= INTEGER (0..4095, ...)

CGI-EUTRA ::= SEQUENCE {
	pLMN-Identity				PLMN-Identity, 
	eUTRAcellIdentifier			EUTRACellIdentifier, 
	iE-Extensions				ProtocolExtensionContainer { {CGI-EUTRA-ExtIEs} } OPTIONAL, 
	...
}

CGI-EUTRA-ExtIEs NRPPA-PROTOCOL-EXTENSION ::= {
	...
}

CPLength-EUTRA ::= ENUMERATED {
	normal, 
	extended, 
	...
}

CriticalityDiagnostics ::= SEQUENCE {
	procedureCode					ProcedureCode					OPTIONAL, 
	triggeringMessage				TriggeringMessage				OPTIONAL, 
	procedureCriticality			Criticality					OPTIONAL, 
	nrppatransactionID				NRPPATransactionID				OPTIONAL, 
	iEsCriticalityDiagnostics		CriticalityDiagnostics-IE-List	OPTIONAL, 
	iE-Extensions					ProtocolExtensionContainer { {CriticalityDiagnostics-ExtIEs} }	OPTIONAL, 
	...
}


CriticalityDiagnostics-ExtIEs NRPPA-PROTOCOL-EXTENSION ::= {
	...
}

CriticalityDiagnostics-IE-List ::= SEQUENCE (SIZE (1..maxNrOfErrors)) OF
	SEQUENCE {
		iECriticality			Criticality, 
		iE-ID					ProtocolIE-ID, 
		typeOfError			TypeOfError, 
		iE-Extensions			ProtocolExtensionContainer { {CriticalityDiagnostics-IE-List-ExtIEs} } OPTIONAL, 
		...
}

CriticalityDiagnostics-IE-List-ExtIEs NRPPA-PROTOCOL-EXTENSION ::= {
	...
}

DL-Bandwidth-EUTRA ::= ENUMERATED {
	bw6, 
	bw15, 
	bw25, 
	bw50, 
	bw75, 
	bw100, 
	...
}

E-CID-MeasurementResult ::= SEQUENCE {
	servingCell-ID					NG-RAN-CGI, 
	servingCellTAC					TAC, 
	nG-RANAccessPointPosition		NG-RANAccessPointPosition	OPTIONAL, 
	measuredResults					MeasuredResults				OPTIONAL, 
	iE-Extensions					ProtocolExtensionContainer { { E-CID-MeasurementResult-ExtIEs} } OPTIONAL, 
	...
}

E-CID-MeasurementResult-ExtIEs NRPPA-PROTOCOL-EXTENSION ::= {
	...
}

EUTRACellIdentifier ::= BIT STRING (SIZE (28))

EARFCN ::= INTEGER (0..262143,  ...)



HESSID ::= OCTET STRING (SIZE(6))





Measurement-ID ::= INTEGER (1..15,  ...)

MeasurementPeriodicity ::= ENUMERATED {
	ms120, 
	ms240, 
	ms480, 
	ms640, 
	ms1024, 
	ms2048, 
	ms5120, 
	ms10240, 
	min1, 
	min6, 
	min12, 
	min30, 
	min60, 
	...
}

MeasurementQuantities ::= SEQUENCE (SIZE (1.. maxNoMeas)) OF ProtocolIE-Single-Container { {MeasurementQuantities-ItemIEs} }

MeasurementQuantities-ItemIEs NRPPA-PROTOCOL-IES ::= {
	{ ID id-MeasurementQuantities-Item	CRITICALITY reject	TYPE MeasurementQuantities-Item		PRESENCE mandatory}
}

MeasurementQuantities-Item ::= SEQUENCE {
	measurementQuantitiesValue					MeasurementQuantitiesValue, 
	iE-Extensions								ProtocolExtensionContainer { { MeasurementQuantitiesValue-ExtIEs} } OPTIONAL, 
	...
}

MeasurementQuantitiesValue-ExtIEs NRPPA-PROTOCOL-EXTENSION ::= {
	...
}

MeasurementQuantitiesValue ::= ENUMERATED {
	cell-ID, 
	angleOfArrival, 
	timingAdvanceType1, 
	timingAdvanceType2, 
	rSRP, 
	rSRQ, 
	...
}

MeasuredResults ::= SEQUENCE (SIZE (1.. maxNoMeas)) OF MeasuredResultsValue

MeasuredResultsValue ::= CHOICE { 
	valueAngleOfArrival-EUTRA				INTEGER (0..719), 
	valueTimingAdvanceType1-EUTRA			INTEGER (0..7690), 
	valueTimingAdvanceType2-EUTRA			INTEGER (0..7690), 
	resultRSRP-EUTRA						ResultRSRP-EUTRA, 
	resultRSRQ-EUTRA						ResultRSRQ-EUTRA, 
	measuredResultsValue-Extension			MeasuredResultsValue-Extension, 
	...
}

MeasuredResultsValue-Extension ::= ProtocolIE-Single-Container {{ MeasuredResultsValue-ExtensionIE }}

MeasuredResultsValue-ExtensionIE NRPPA-PROTOCOL-IES ::= {
	...
}

NarrowBandIndex ::= INTEGER (0..15, ...)

NG-RANAccessPointPosition ::= SEQUENCE {
	latitudeSign				ENUMERATED {north,  south}, 
	latitude					INTEGER (0..8388607), 
	longitude					INTEGER (-8388608..8388607), 
	directionOfAltitude			ENUMERATED {height,  depth}, 
	altitude					INTEGER (0..32767), 
	uncertaintySemi-major		INTEGER (0..127), 
	uncertaintySemi-minor		INTEGER (0..127), 
	orientationOfMajorAxis		INTEGER (0..179), 
	uncertaintyAltitude			INTEGER (0..127), 
	confidence					INTEGER (0..100), 
	iE-Extensions				ProtocolExtensionContainer { { NG-RANAccessPointPosition-ExtIEs} } OPTIONAL, 
	...
}

NG-RANAccessPointPosition-ExtIEs NRPPA-PROTOCOL-EXTENSION ::= {
	...
}

NG-RAN-CGI ::= SEQUENCE {
	pLMN-Identity				PLMN-Identity, 
	nG-RANcell		NG-RANCell, 
	iE-Extensions				ProtocolExtensionContainer { {NG-RAN-CGI-ExtIEs} } OPTIONAL, 
	...
}

NG-RAN-CGI-ExtIEs NRPPA-PROTOCOL-EXTENSION ::= {
	...
}

NG-RANCell ::= CHOICE {
	eUTRA-CellID	EUTRACellIdentifier, 
	nR-CellID		NRCellIdentifier, 
	...
}

NRCellIdentifier ::= BIT STRING (SIZE (36))

NumberOfAntennaPorts-EUTRA ::= ENUMERATED {
		n1-or-n2, 
		n4, 
		...
}

NumberOfDlFrames-EUTRA ::= ENUMERATED {
		sf1, 
		sf2, 
		sf4, 
		sf6, 
		...
}

NumberOfDlFrames-Extended-EUTRA ::= INTEGER (1..160, ...)

NumberOfFrequencyHoppingBands ::= ENUMERATED {
	twobands, 
	fourbands, 
	...
}

OTDOACells ::= SEQUENCE (SIZE (1.. maxCellinRANnode)) OF SEQUENCE {
	oTDOACellInfo					OTDOACell-Information, 
	iE-Extensions					ProtocolExtensionContainer { {OTDOACells-ExtIEs} } OPTIONAL, 
	...
}

OTDOACells-ExtIEs NRPPA-PROTOCOL-EXTENSION ::= {
	...
}

OTDOACell-Information ::= SEQUENCE (SIZE (1..maxnoOTDOAtypes)) OF OTDOACell-Information-Item

OTDOACell-Information-Item ::= CHOICE {
	pCI-EUTRA									PCI-EUTRA, 
	cGI-EUTRA									CGI-EUTRA, 
	tAC											TAC, 
	eARFCN										EARFCN, 
	pRS-Bandwidth-EUTRA							PRS-Bandwidth-EUTRA, 
	pRS-ConfigurationIndex-EUTRA				PRS-ConfigurationIndex-EUTRA,  
	cPLength-EUTRA								CPLength-EUTRA, 
	numberOfDlFrames-EUTRA						NumberOfDlFrames-EUTRA, 
	numberOfAntennaPorts-EUTRA					NumberOfAntennaPorts-EUTRA, 
	sFNInitialisationTime-EUTRA					SFNInitialisationTime-EUTRA, 
	nG-RANAccessPointPosition					NG-RANAccessPointPosition, 
	pRSMutingConfiguration-EUTRA				PRSMutingConfiguration-EUTRA, 
	prsid-EUTRA									PRS-ID-EUTRA, 
	tpid-EUTRA									TP-ID-EUTRA, 
	tpType-EUTRA								TP-Type-EUTRA, 
	numberOfDlFrames-Extended-EUTRA				NumberOfDlFrames-Extended-EUTRA, 
	crsCPlength-EUTRA							CPLength-EUTRA, 
	dL-Bandwidth-EUTRA							DL-Bandwidth-EUTRA, 
	pRSOccasionGroup-EUTRA						PRSOccasionGroup-EUTRA, 
	pRSFrequencyHoppingConfiguration-EUTRA		PRSFrequencyHoppingConfiguration-EUTRA, 
	...
}

OTDOA-Information-Item ::= ENUMERATED {
		pci, 
		cGI, 
		tac, 
		earfcn, 
		prsBandwidth, 
		prsConfigIndex, 
		cpLength, 
		noDlFrames, 
		noAntennaPorts, 
		sFNInitTime, 
		nG-RANAccessPointPosition, 
		prsmutingconfiguration, 
		prsid, 
		tpid, 
		tpType, 
		crsCPlength, 
		dlBandwidth,  
		multipleprsConfigurationsperCell, 
		prsOccasionGroup, 
		prsFrequencyHoppingConfiguration, 
		...
}

OtherRATMeasurementQuantities ::= SEQUENCE (SIZE (0.. maxNoMeas)) OF ProtocolIE-Single-Container { {OtherRATMeasurementQuantities-ItemIEs} }

OtherRATMeasurementQuantities-ItemIEs NRPPA-PROTOCOL-IES ::= {
	{ ID id-OtherRATMeasurementQuantities-Item	CRITICALITY reject	TYPE OtherRATMeasurementQuantities-Item PRESENCE mandatory}}

OtherRATMeasurementQuantities-Item ::= SEQUENCE {
	otherRATMeasurementQuantitiesValue			OtherRATMeasurementQuantitiesValue, 
	iE-Extensions								ProtocolExtensionContainer { { OtherRATMeasurementQuantitiesValue-ExtIEs} } OPTIONAL, 
	...
}

OtherRATMeasurementQuantitiesValue-ExtIEs NRPPA-PROTOCOL-EXTENSION ::= {
	...
}

OtherRATMeasurementQuantitiesValue ::= ENUMERATED {
	geran, 
	utran, 
	...
}

OtherRATMeasurementResult ::= SEQUENCE (SIZE (1.. maxNoMeas)) OF OtherRATMeasuredResultsValue

OtherRATMeasuredResultsValue ::= CHOICE {
	resultGERAN			ResultGERAN, 
	resultUTRAN			ResultUTRAN, 
	...
}

PCI-EUTRA ::= INTEGER (0..503,  ...)

PhysCellIDGERAN ::= INTEGER (0..63,  ...)

PhysCellIDUTRA-FDD ::= INTEGER (0..511,  ...)

PhysCellIDUTRA-TDD ::= INTEGER (0..127,  ...)

PLMN-Identity ::= OCTET STRING (SIZE(3))

PRS-Bandwidth-EUTRA ::= ENUMERATED {
		bw6, 
		bw15, 
		bw25, 
		bw50, 
		bw75, 
		bw100, 
		...
}

PRS-ConfigurationIndex-EUTRA ::= INTEGER (0..4095,  ...)

PRS-ID-EUTRA	::= INTEGER (0..4095,  ...)

PRSMutingConfiguration-EUTRA ::= CHOICE {
	two 							BIT STRING (SIZE (2)), 
	four 							BIT STRING (SIZE (4)), 
	eight 							BIT STRING (SIZE (8)), 
	sixteen 						BIT STRING (SIZE (16)), 
	thirty-two						BIT STRING (SIZE (32)), 
	sixty-four						BIT STRING (SIZE (64)), 
	one-hundred-and-twenty-eight	BIT STRING (SIZE (128)), 
	two-hundred-and-fifty-six		BIT STRING (SIZE (256)), 
	five-hundred-and-twelve			BIT STRING (SIZE (512)), 
	one-thousand-and-twenty-four	BIT STRING (SIZE (1024)), 
	...
}

PRSOccasionGroup-EUTRA ::= ENUMERATED {
	og2, 
	og4, 
	og8, 
	og16, 
	og32, 
	og64, 
	og128, 
	...
}

PRSFrequencyHoppingConfiguration-EUTRA ::= SEQUENCE {
	noOfFreqHoppingBands		NumberOfFrequencyHoppingBands, 
	bandPositions				SEQUENCE(SIZE (1..maxnoFreqHoppingBandsMinusOne)) OF NarrowBandIndex, 
	iE-Extensions				ProtocolExtensionContainer { { PRSFrequencyHoppingConfiguration-EUTRA-Item-IEs} } OPTIONAL, 
	...
}

PRSFrequencyHoppingConfiguration-EUTRA-Item-IEs NRPPA-PROTOCOL-EXTENSION ::= {
	...
}


ReportCharacteristics ::= ENUMERATED {
	onDemand, 
	periodic, 
	...
}

RequestedSRSTransmissionCharacteristics ::= SEQUENCE {
	numberOfTransmissions	INTEGER (0..500,  ...), 
	bandwidth				INTEGER (1..100,  ...), 
	iE-Extensions			ProtocolExtensionContainer { { RequestedSRSTransmissionCharacteristics-ExtIEs} } OPTIONAL, 
	...
}

RequestedSRSTransmissionCharacteristics-ExtIEs NRPPA-PROTOCOL-EXTENSION ::= {
	...
}

ResultRSRP-EUTRA ::= SEQUENCE (SIZE (1.. maxCellReport)) OF ResultRSRP-EUTRA-Item

ResultRSRP-EUTRA-Item ::= SEQUENCE {
	pCI-EUTRA			PCI-EUTRA, 
	eARFCN				EARFCN, 
	cGI-EUTRA			CGI-EUTRA OPTIONAL, 
	valueRSRP-EUTRA		ValueRSRP-EUTRA, 
	iE-Extensions		ProtocolExtensionContainer { { ResultRSRP-EUTRA-Item-ExtIEs} } OPTIONAL, 
	...
}

ResultRSRP-EUTRA-Item-ExtIEs NRPPA-PROTOCOL-EXTENSION ::= {
	...
}

ResultRSRQ-EUTRA ::= SEQUENCE (SIZE (1.. maxCellReport)) OF ResultRSRQ-EUTRA-Item

ResultRSRQ-EUTRA-Item ::= SEQUENCE {
	pCI-EUTRA			PCI-EUTRA, 
	eARFCN				EARFCN, 
	cGI-UTRA			CGI-EUTRA OPTIONAL, 
	valueRSRQ-EUTRA		ValueRSRQ-EUTRA, 
	iE-Extensions		ProtocolExtensionContainer { { ResultRSRQ-EUTRA-Item-ExtIEs} } OPTIONAL, 
	...
}

ResultRSRQ-EUTRA-Item-ExtIEs NRPPA-PROTOCOL-EXTENSION ::= {
	...
}

ResultGERAN ::= SEQUENCE (SIZE (1.. maxGERANMeas)) OF ResultGERAN-Item

ResultGERAN-Item ::= SEQUENCE {
	bCCH				BCCH, 
	physCellIDGERAN		PhysCellIDGERAN, 
	rSSI				RSSI, 
	iE-Extensions		ProtocolExtensionContainer { { ResultGERAN-Item-ExtIEs} } OPTIONAL, 
	...
}

ResultGERAN-Item-ExtIEs NRPPA-PROTOCOL-EXTENSION ::= {
	...
}

ResultUTRAN ::= SEQUENCE (SIZE (1.. maxUTRANMeas)) OF ResultUTRAN-Item

ResultUTRAN-Item ::= SEQUENCE {
	uARFCN				UARFCN, 
	physCellIDUTRAN		CHOICE {
		physCellIDUTRA-FDD		PhysCellIDUTRA-FDD, 
		physCellIDUTRA-TDD		PhysCellIDUTRA-TDD
	}, 
	uTRA-RSCP			UTRA-RSCP OPTIONAL, 
	uTRA-EcN0			UTRA-EcN0 OPTIONAL, 
	iE-Extensions		ProtocolExtensionContainer { { ResultUTRAN-Item-ExtIEs} } OPTIONAL, 
	...
}

ResultUTRAN-Item-ExtIEs NRPPA-PROTOCOL-EXTENSION ::= {
	...
}

RSSI ::= INTEGER (0..63,  ...)

SFNInitialisationTime-EUTRA ::= BIT STRING (SIZE (64))

SSID ::= OCTET STRING (SIZE(1..32))

TAC ::= OCTET STRING (SIZE(3))

TP-ID-EUTRA ::= INTEGER (0..4095,  ...)

TP-Type-EUTRA ::= ENUMERATED { prs-only-tp,  ... }

TypeOfError ::= ENUMERATED {
	not-understood, 
	missing, 
	...
}

UARFCN ::= INTEGER (0..16383,  ...)

UTRA-EcN0 ::= INTEGER (0..49,  ...)

UTRA-RSCP ::= INTEGER (-5..91,  ...)

ValueRSRP-EUTRA ::= INTEGER (0..97,  ...)

ValueRSRQ-EUTRA ::= INTEGER (0..34,  ...)

WLANMeasurementQuantities ::= SEQUENCE (SIZE (0.. maxNoMeas)) OF ProtocolIE-Single-Container { {WLANMeasurementQuantities-ItemIEs} }

WLANMeasurementQuantities-ItemIEs NRPPA-PROTOCOL-IES ::= {
	{ ID id-WLANMeasurementQuantities-Item	CRITICALITY reject	TYPE WLANMeasurementQuantities-Item PRESENCE mandatory}}

WLANMeasurementQuantities-Item ::= SEQUENCE {
	wLANMeasurementQuantitiesValue			WLANMeasurementQuantitiesValue, 
	iE-Extensions							ProtocolExtensionContainer { { WLANMeasurementQuantitiesValue-ExtIEs} } OPTIONAL, 
	...
}

WLANMeasurementQuantitiesValue-ExtIEs NRPPA-PROTOCOL-EXTENSION ::= {
	...
}

WLANMeasurementQuantitiesValue ::= ENUMERATED {
	wlan, 
	...
}

WLANMeasurementResult ::= SEQUENCE (SIZE (1..maxNoMeas)) OF WLANMeasurementResult-Item

WLANMeasurementResult-Item ::= SEQUENCE {
	wLAN-RSSI			WLAN-RSSI, 
	sSID				SSID					OPTIONAL, 
	bSSID				BSSID					OPTIONAL, 
	hESSID				HESSID					OPTIONAL, 
	operatingClass		WLANOperatingClass		OPTIONAL, 
	countryCode			WLANCountryCode			OPTIONAL, 
	wLANChannelList		WLANChannelList			OPTIONAL, 
	wLANBand			WLANBand				OPTIONAL, 
	iE-Extensions		ProtocolExtensionContainer { { WLANMeasurementResult-Item-ExtIEs } }	OPTIONAL, 
	...
}

WLANMeasurementResult-Item-ExtIEs	NRPPA-PROTOCOL-EXTENSION ::= {
	...
}

WLAN-RSSI ::= INTEGER (0..141,  ...)

WLANBand ::= ENUMERATED {band2dot4,  band5,  ...}

WLANChannelList ::= SEQUENCE (SIZE (1..maxWLANchannels)) OF WLANChannel

WLANChannel ::= INTEGER (0..255)

WLANCountryCode ::= ENUMERATED {
	unitedStates, 
	europe, 
	japan, 
	global, 
	...
}

WLANOperatingClass ::= INTEGER (0..255)



END





NRPPA-CommonDataTypes {
itu-t (0) identified-organization (4) etsi (0) mobileDomain (0) 
ngran-access (22) modules (3) nrppa (4) version1 (1) nrppa-CommonDataTypes (3)}

DEFINITIONS AUTOMATIC TAGS ::= 

BEGIN





maxPrivateIEs 									INTEGER ::= 65535
maxProtocolExtensions 							INTEGER ::= 65535
maxProtocolIEs									INTEGER ::= 65535





Criticality		::= ENUMERATED { reject,  ignore,  notify }

NRPPATransactionID		::= INTEGER (0..32767)


Presence		::= ENUMERATED { optional,  conditional,  mandatory }

PrivateIE-ID	::= CHOICE {
	local			INTEGER (0.. maxPrivateIEs), 
	global			OBJECT IDENTIFIER
}

ProcedureCode		::= INTEGER (0..255)

ProtocolIE-ID		::= INTEGER (0..maxProtocolIEs)

TriggeringMessage	::= ENUMERATED { initiating-message,  successful-outcome,  unsuccessful-outcome}

END





NRPPA-Constants {
itu-t (0) identified-organization (4) etsi (0) mobileDomain (0) 
ngran-access (22) modules (3) nrppa (4) version1 (1) nrppa-Constants (4) }

DEFINITIONS AUTOMATIC TAGS ::= 

BEGIN

IMPORTS

	ProcedureCode, 
	ProtocolIE-ID
FROM NRPPA-CommonDataTypes;





id-errorIndication												ProcedureCode ::= 0
id-privateMessage												ProcedureCode ::= 1
id-e-CIDMeasurementInitiation									ProcedureCode ::= 2
id-e-CIDMeasurementFailureIndication							ProcedureCode ::= 3
id-e-CIDMeasurementReport										ProcedureCode ::= 4
id-e-CIDMeasurementTermination									ProcedureCode ::= 5
id-oTDOAInformationExchange										ProcedureCode ::= 6





maxNrOfErrors								INTEGER ::= 256
maxCellinRANnode							INTEGER ::= 3840
maxNoMeas									INTEGER ::= 63
maxCellReport								INTEGER ::= 9
maxnoOTDOAtypes								INTEGER ::= 63
maxServCell									INTEGER ::= 5
maxGERANMeas								INTEGER ::= 8
maxUTRANMeas								INTEGER ::= 8
maxWLANchannels								INTEGER ::= 16 
maxnoFreqHoppingBandsMinusOne				INTEGER ::= 7





id-Cause														ProtocolIE-ID ::= 0
id-CriticalityDiagnostics										ProtocolIE-ID ::= 1
id-LMF-UE-Measurement-ID										ProtocolIE-ID ::= 2
id-ReportCharacteristics										ProtocolIE-ID ::= 3
id-MeasurementPeriodicity										ProtocolIE-ID ::= 4
id-MeasurementQuantities										ProtocolIE-ID ::= 5
id-RAN-UE-Measurement-ID										ProtocolIE-ID ::= 6
id-E-CID-MeasurementResult										ProtocolIE-ID ::= 7
id-OTDOACells													ProtocolIE-ID ::= 8
id-OTDOA-Information-Type-Group									ProtocolIE-ID ::= 9
id-OTDOA-Information-Type-Item									ProtocolIE-ID ::= 10
id-MeasurementQuantities-Item									ProtocolIE-ID ::= 11
id-RequestedSRSTransmissionCharacteristics						ProtocolIE-ID ::= 12
id-Cell-Portion-ID												ProtocolIE-ID ::= 14
id-OtherRATMeasurementQuantities								ProtocolIE-ID ::= 15
id-OtherRATMeasurementQuantities-Item							ProtocolIE-ID ::= 16
id-OtherRATMeasurementResult									ProtocolIE-ID ::= 17
id-WLANMeasurementQuantities									ProtocolIE-ID ::= 19
id-WLANMeasurementQuantities-Item								ProtocolIE-ID ::= 20
id-WLANMeasurementResult										ProtocolIE-ID ::= 21

END





NRPPA-Containers {
itu-t (0) identified-organization (4) etsi (0) mobileDomain (0) 
ngran-access (22) modules (3) nrppa (4) version1 (1) nrppa-Containers (5)}

DEFINITIONS AUTOMATIC TAGS ::= 

BEGIN





IMPORTS
	maxPrivateIEs, 
	maxProtocolExtensions, 
	maxProtocolIEs, 
	Criticality, 
	Presence, 
	PrivateIE-ID, 
	ProtocolIE-ID	
FROM NRPPA-CommonDataTypes;





NRPPA-PROTOCOL-IES ::= CLASS {
	&id					ProtocolIE-ID			UNIQUE, 
	&criticality		Criticality, 
	&Value, 
	&presence			Presence
}
WITH SYNTAX {
	ID					&id
	CRITICALITY			&criticality
	TYPE				&Value
	PRESENCE			&presence
}





NRPPA-PROTOCOL-EXTENSION ::= CLASS {
	&id					ProtocolIE-ID		UNIQUE, 
	&criticality		Criticality, 
	&Extension, 
	&presence			Presence
}
WITH SYNTAX {
	ID					&id
	CRITICALITY			&criticality
	EXTENSION			&Extension
	PRESENCE			&presence
}





NRPPA-PRIVATE-IES ::= CLASS {
	&id					PrivateIE-ID, 
	&criticality		Criticality, 
	&Value, 
	&presence			Presence
}
WITH SYNTAX {
	ID					&id
	CRITICALITY			&criticality
	TYPE				&Value
	PRESENCE			&presence
}





ProtocolIE-Container { NRPPA-PROTOCOL-IES : IEsSetParam} ::= 
	SEQUENCE (SIZE (0..maxProtocolIEs)) OF
	ProtocolIE-Field {{IEsSetParam}}

ProtocolIE-Single-Container { NRPPA-PROTOCOL-IES : IEsSetParam} ::= 
	ProtocolIE-Field {{IEsSetParam}}

ProtocolIE-Field { NRPPA-PROTOCOL-IES : IEsSetParam} ::= SEQUENCE {
	id				NRPPA-PROTOCOL-IES.&id				({IEsSetParam}), 
	criticality		NRPPA-PROTOCOL-IES.&criticality		({IEsSetParam}{@id}), 
	value			NRPPA-PROTOCOL-IES.&Value			({IEsSetParam}{@id})
}





ProtocolIE-ContainerList {INTEGER : lowerBound,  INTEGER : upperBound,  NRPPA-PROTOCOL-IES : IEsSetParam} ::=
	SEQUENCE (SIZE (lowerBound..upperBound)) OF
	ProtocolIE-Container {{IEsSetParam}}





ProtocolExtensionContainer { NRPPA-PROTOCOL-EXTENSION : ExtensionSetParam} ::= 
	SEQUENCE (SIZE (1..maxProtocolExtensions)) OF
	ProtocolExtensionField {{ExtensionSetParam}}

ProtocolExtensionField { NRPPA-PROTOCOL-EXTENSION : ExtensionSetParam} ::= SEQUENCE {
	id					NRPPA-PROTOCOL-EXTENSION.&id			({ExtensionSetParam}), 
	criticality			NRPPA-PROTOCOL-EXTENSION.&criticality	({ExtensionSetParam}{@id}), 
	extensionValue		NRPPA-PROTOCOL-EXTENSION.&Extension		({ExtensionSetParam}{@id})
}





PrivateIE-Container { NRPPA-PRIVATE-IES : IEsSetParam} ::= 
	SEQUENCE (SIZE (1..maxPrivateIEs)) OF
	PrivateIE-Field {{IEsSetParam}}

PrivateIE-Field { NRPPA-PRIVATE-IES : IEsSetParam} ::= SEQUENCE {
	id				NRPPA-PRIVATE-IES.&id				({IEsSetParam}), 
	criticality		NRPPA-PRIVATE-IES.&criticality		({IEsSetParam}{@id}), 
	value			NRPPA-PRIVATE-IES.&Value			({IEsSetParam}{@id})
}

END
