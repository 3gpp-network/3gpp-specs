NRPPA-PDU-Descriptions {
itu-t (0) identified-organization (4) etsi (0) mobileDomain (0)
ngran-access (22) modules (3) nrppa (4) version1 (1) nrppa-PDU-Descriptions (0) }

DEFINITIONS AUTOMATIC TAGS ::= 

BEGIN





IMPORTS
	Criticality, 
	ProcedureCode, 
	NRPPATransactionID

FROM NRPPA-CommonDataTypes


	ErrorIndication, 
	PrivateMessage, 
	E-CIDMeasurementInitiationRequest, 
	E-CIDMeasurementInitiationResponse, 
	E-CIDMeasurementInitiationFailure, 
	E-CIDMeasurementFailureIndication, 
	E-CIDMeasurementReport, 
	E-CIDMeasurementTerminationCommand, 
	OTDOAInformationRequest, 
	OTDOAInformationResponse, 
	OTDOAInformationFailure, 
	AssistanceInformationControl, 
	AssistanceInformationFeedback, 
	PositioningInformationRequest, 
	PositioningInformationResponse, 
	PositioningInformationFailure, 
	PositioningInformationUpdate, 
	MeasurementRequest, 
	MeasurementResponse, 
	MeasurementFailure, 
	MeasurementReport, 
	MeasurementUpdate, 
	MeasurementAbort, 
	MeasurementFailureIndication, 
	TRPInformationRequest, 
	TRPInformationResponse, 
	TRPInformationFailure, 
	PositioningActivationRequest, 
	PositioningActivationResponse, 
	PositioningActivationFailure, 
	PositioningDeactivation


FROM NRPPA-PDU-Contents

	id-errorIndication, 
	id-privateMessage, 
	id-e-CIDMeasurementInitiation, 
	id-e-CIDMeasurementFailureIndication, 
	id-e-CIDMeasurementReport, 
	id-e-CIDMeasurementTermination, 
	id-oTDOAInformationExchange, 
	id-assistanceInformationControl, 
	id-assistanceInformationFeedback, 
	id-positioningInformationExchange, 
	id-positioningInformationUpdate, 
	id-Measurement, 
	id-MeasurementReport, 
	id-MeasurementUpdate, 
	id-MeasurementAbort, 
	id-MeasurementFailureIndication, 
	id-tRPInformationExchange,  
	id-positioningActivation, 
	id-positioningDeactivation



FROM NRPPA-Constants;





NRPPA-ELEMENTARY-PROCEDURE ::= CLASS {
	&InitiatingMessage				, 
	&SuccessfulOutcome							OPTIONAL, 
	&UnsuccessfulOutcome						OPTIONAL, 
	&procedureCode				ProcedureCode	UNIQUE, 
	&criticality				Criticality	DEFAULT ignore
}
WITH SYNTAX {
	INITIATING MESSAGE			&InitiatingMessage
	[SUCCESSFUL OUTCOME		&SuccessfulOutcome]
	[UNSUCCESSFUL OUTCOME		&UnsuccessfulOutcome]
	PROCEDURE CODE				&procedureCode
	[CRITICALITY				&criticality]
}





NRPPA-PDU ::= CHOICE {
	initiatingMessage		InitiatingMessage, 
	successfulOutcome		SuccessfulOutcome, 
	unsuccessfulOutcome	UnsuccessfulOutcome, 
	...
}

InitiatingMessage ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&InitiatingMessage	({NRPPA-ELEMENTARY-PROCEDURES}{@procedureCode})
}

SuccessfulOutcome ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&SuccessfulOutcome	({NRPPA-ELEMENTARY-PROCEDURES}{@procedureCode})
}

UnsuccessfulOutcome ::= SEQUENCE {
	procedureCode			NRPPA-ELEMENTARY-PROCEDURE.&procedureCode		({NRPPA-ELEMENTARY-PROCEDURES}), 
	criticality			NRPPA-ELEMENTARY-PROCEDURE.&criticality			({NRPPA-ELEMENTARY-PROCEDURES}{@procedureCode}), 
	nrppatransactionID		NRPPATransactionID, 
	value					NRPPA-ELEMENTARY-PROCEDURE.&UnsuccessfulOutcome	({NRPPA-ELEMENTARY-PROCEDURES}{@procedureCode})
}





NRPPA-ELEMENTARY-PROCEDURES NRPPA-ELEMENTARY-PROCEDURE ::= {
	NRPPA-ELEMENTARY-PROCEDURES-CLASS-1			|
	NRPPA-ELEMENTARY-PROCEDURES-CLASS-2			, 
	...
}

NRPPA-ELEMENTARY-PROCEDURES-CLASS-1 NRPPA-ELEMENTARY-PROCEDURE ::= {
	e-CIDMeasurementInitiation	|
	oTDOAInformationExchange	|
	positioningInformationExchange	|
	measurement						|
	tRPInformationExchange		|
	positioningActivation, 
	...
}

NRPPA-ELEMENTARY-PROCEDURES-CLASS-2 NRPPA-ELEMENTARY-PROCEDURE ::= {
	e-CIDMeasurementFailureIndication		|
	e-CIDMeasurementReport					|
	e-CIDMeasurementTermination				|
	errorIndication							|
	privateMessage							|
	assistanceInformationControl			|
	assistanceInformationFeedback 			|
	positioningInformationUpdate			|
	measurementReport						|
	measurementUpdate						|
	measurementAbort						|
	measurementFailureIndication		|
	positioningDeactivation, 
	...
}





e-CIDMeasurementInitiation NRPPA-ELEMENTARY-PROCEDURE ::= {
	INITIATING MESSAGE		E-CIDMeasurementInitiationRequest
	SUCCESSFUL OUTCOME		E-CIDMeasurementInitiationResponse
	UNSUCCESSFUL OUTCOME	E-CIDMeasurementInitiationFailure
	PROCEDURE CODE			id-e-CIDMeasurementInitiation
	CRITICALITY				reject
}

e-CIDMeasurementFailureIndication NRPPA-ELEMENTARY-PROCEDURE ::= {
	INITIATING MESSAGE		E-CIDMeasurementFailureIndication
	PROCEDURE CODE			id-e-CIDMeasurementFailureIndication
	CRITICALITY				ignore
}

e-CIDMeasurementReport NRPPA-ELEMENTARY-PROCEDURE ::= {
	INITIATING MESSAGE		E-CIDMeasurementReport
	PROCEDURE CODE			id-e-CIDMeasurementReport
	CRITICALITY				ignore
}

e-CIDMeasurementTermination NRPPA-ELEMENTARY-PROCEDURE ::= {
	INITIATING MESSAGE		E-CIDMeasurementTerminationCommand
	PROCEDURE CODE			id-e-CIDMeasurementTermination
	CRITICALITY				reject
}

oTDOAInformationExchange NRPPA-ELEMENTARY-PROCEDURE ::= {
	INITIATING MESSAGE		OTDOAInformationRequest
	SUCCESSFUL OUTCOME		OTDOAInformationResponse
	UNSUCCESSFUL OUTCOME	OTDOAInformationFailure
	PROCEDURE CODE			id-oTDOAInformationExchange
	CRITICALITY				reject
}


assistanceInformationControl NRPPA-ELEMENTARY-PROCEDURE ::= {
	INITIATING MESSAGE		AssistanceInformationControl
	PROCEDURE CODE			id-assistanceInformationControl
	CRITICALITY				reject
}

assistanceInformationFeedback NRPPA-ELEMENTARY-PROCEDURE ::= {
	INITIATING MESSAGE		AssistanceInformationFeedback
	PROCEDURE CODE			id-assistanceInformationFeedback
	CRITICALITY				reject
}


errorIndication NRPPA-ELEMENTARY-PROCEDURE ::= {
	INITIATING MESSAGE		ErrorIndication
	PROCEDURE CODE			id-errorIndication
	CRITICALITY			ignore
}


privateMessage			NRPPA-ELEMENTARY-PROCEDURE ::= {
	INITIATING MESSAGE		PrivateMessage
	PROCEDURE CODE			id-privateMessage
	CRITICALITY			ignore
}


positioningInformationExchange	NRPPA-ELEMENTARY-PROCEDURE ::= {
	INITIATING MESSAGE		PositioningInformationRequest
	SUCCESSFUL OUTCOME		PositioningInformationResponse
	UNSUCCESSFUL OUTCOME	PositioningInformationFailure
	PROCEDURE CODE			id-positioningInformationExchange
	CRITICALITY				reject
}

positioningInformationUpdate	NRPPA-ELEMENTARY-PROCEDURE ::= {
	INITIATING MESSAGE		PositioningInformationUpdate
	PROCEDURE CODE			id-positioningInformationUpdate
	CRITICALITY				ignore
}

measurement	NRPPA-ELEMENTARY-PROCEDURE ::= {
	INITIATING MESSAGE		MeasurementRequest
	SUCCESSFUL OUTCOME		MeasurementResponse
	UNSUCCESSFUL OUTCOME	MeasurementFailure
	PROCEDURE CODE			id-Measurement
	CRITICALITY				reject
}

measurementReport	NRPPA-ELEMENTARY-PROCEDURE ::= {
	INITIATING MESSAGE		MeasurementReport
	PROCEDURE CODE			id-MeasurementReport
	CRITICALITY				ignore
}

measurementUpdate	NRPPA-ELEMENTARY-PROCEDURE ::= {
	INITIATING MESSAGE		MeasurementUpdate
	PROCEDURE CODE			id-MeasurementUpdate
	CRITICALITY				ignore
}

measurementAbort	NRPPA-ELEMENTARY-PROCEDURE ::= {
	INITIATING MESSAGE		MeasurementAbort
	PROCEDURE CODE			id-MeasurementAbort
	CRITICALITY				ignore
}

measurementFailureIndication	NRPPA-ELEMENTARY-PROCEDURE ::= {
	INITIATING MESSAGE		MeasurementFailureIndication
	PROCEDURE CODE			id-MeasurementFailureIndication
	CRITICALITY				ignore
}

tRPInformationExchange	NRPPA-ELEMENTARY-PROCEDURE ::= {
	INITIATING MESSAGE		TRPInformationRequest
	SUCCESSFUL OUTCOME		TRPInformationResponse
	UNSUCCESSFUL OUTCOME	TRPInformationFailure
	PROCEDURE CODE			id-tRPInformationExchange
	CRITICALITY				reject
}

positioningActivation NRPPA-ELEMENTARY-PROCEDURE ::= {
	INITIATING MESSAGE		PositioningActivationRequest
	SUCCESSFUL OUTCOME		PositioningActivationResponse
	UNSUCCESSFUL OUTCOME	PositioningActivationFailure
	PROCEDURE CODE			id-positioningActivation
	CRITICALITY				reject
}

positioningDeactivation NRPPA-ELEMENTARY-PROCEDURE ::= {
	INITIATING MESSAGE		PositioningDeactivation
	PROCEDURE CODE			id-positioningDeactivation
	CRITICALITY				ignore
}


END





NRPPA-PDU-Contents {
itu-t (0) identified-organization (4) etsi (0) mobileDomain (0) 
ngran-access (22) modules (3) nrppa (4) version1 (1) nrppa-PDU-Contents (1) }

DEFINITIONS AUTOMATIC TAGS ::= 

BEGIN





IMPORTS
	
	Cause, 
	CriticalityDiagnostics, 
	E-CID-MeasurementResult, 
	OTDOACells, 
	OTDOA-Information-Item, 
	Measurement-ID, 
	UE-Measurement-ID, 
	MeasurementPeriodicity, 
	MeasurementQuantities, 
	ReportCharacteristics, 
	RequestedSRSTransmissionCharacteristics, 
	Cell-Portion-ID, 
	OtherRATMeasurementQuantities, 
	OtherRATMeasurementResult, 
	WLANMeasurementQuantities, 
	WLANMeasurementResult, 
	Assistance-Information, 
	Broadcast, 
	AssistanceInformationFailureList, 
	SRSConfiguration, 
	TRPMeasurementQuantities, 
	TrpMeasurementResult, 
	TRP-ID, 
	TRPInformationTypeList, 
	TRPInformationList, 
	TRP-MeasurementRequestList, 
	TRP-MeasurementResponseList, 
	MeasurementBeamInfoRequest, 
	PositioningBroadcastCells, 
	ActivationTime, 
	SRSResourceSetID, 
	SRSSpatialRelation, 
	SRSResourceTrigger, 
	TRPList, 
	AbortTransmission, 
	SystemFrameNumber, 
	SlotNumber, 
	SFNInitialisationTime

	
FROM NRPPA-IEs

	PrivateIE-Container{}, 
	ProtocolExtensionContainer{}, 
	ProtocolIE-Container{}, 
	ProtocolIE-ContainerList{}, 
	ProtocolIE-Single-Container{}, 
	NRPPA-PRIVATE-IES, 
	NRPPA-PROTOCOL-EXTENSION, 
	NRPPA-PROTOCOL-IES
FROM NRPPA-Containers

	
	maxnoOTDOAtypes, 
	id-Cause, 
	id-CriticalityDiagnostics, 
	id-LMF-Measurement-ID, 
	id-LMF-UE-Measurement-ID, 
	id-OTDOACells, 
	id-OTDOA-Information-Type-Group, 
	id-OTDOA-Information-Type-Item, 
	id-ReportCharacteristics, 
	id-MeasurementPeriodicity, 
	id-MeasurementQuantities, 
	id-RAN-Measurement-ID, 
	id-RAN-UE-Measurement-ID, 
	id-E-CID-MeasurementResult, 
	id-RequestedSRSTransmissionCharacteristics, 
	id-Cell-Portion-ID, 
	id-OtherRATMeasurementQuantities, 
	id-OtherRATMeasurementResult, 
	id-WLANMeasurementQuantities, 
	id-WLANMeasurementResult, 
	id-Assistance-Information, 
	id-Broadcast, 
	id-AssistanceInformationFailureList, 
	id-SRSConfiguration, 
	id-TRPMeasurementQuantities, 
	id-MeasurementResult, 
	id-TRP-ID, 
	id-TRPInformationTypeList, 
	id-TRPInformationList, 	
	id-TRP-MeasurementRequestList, 
	id-TRP-MeasurementResponseList, 
	id-TRP-MeasurementReportList, 
	id-MeasurementBeamInfoRequest, 
	id-PositioningBroadcastCells, 
	id-SRSType, 
	id-ActivationTime, 
	id-SRSResourceSetID, 
	id-TRPList, 
	id-SRSSpatialRelation, 
	id-AbortTransmission,  
	id-SystemFrameNumber, 
	id-SlotNumber, 
	id-SRSResourceTrigger, 
	id-SFNInitialisationTime


	
FROM NRPPA-Constants;





E-CIDMeasurementInitiationRequest ::= SEQUENCE {
	protocolIEs		ProtocolIE-Container	{{E-CIDMeasurementInitiationRequest-IEs}}, 
	...
}

E-CIDMeasurementInitiationRequest-IEs NRPPA-PROTOCOL-IES ::= {
	{ ID id-LMF-UE-Measurement-ID			CRITICALITY reject	TYPE UE-Measurement-ID						PRESENCE mandatory}|
	{ ID id-ReportCharacteristics			CRITICALITY reject	TYPE ReportCharacteristics				PRESENCE mandatory}|
	{ ID id-MeasurementPeriodicity			CRITICALITY reject	TYPE MeasurementPeriodicity				PRESENCE conditional}|

	{ ID id-MeasurementQuantities			CRITICALITY reject	TYPE MeasurementQuantities				PRESENCE mandatory}|
	{ ID id-OtherRATMeasurementQuantities	CRITICALITY ignore	TYPE OtherRATMeasurementQuantities		PRESENCE optional}|
	{ ID id-WLANMeasurementQuantities		CRITICALITY ignore	TYPE WLANMeasurementQuantities			PRESENCE optional}, 
	...
}





E-CIDMeasurementInitiationResponse ::= SEQUENCE {
	protocolIEs		ProtocolIE-Container	{{E-CIDMeasurementInitiationResponse-IEs}}, 
	...
}

E-CIDMeasurementInitiationResponse-IEs NRPPA-PROTOCOL-IES ::= {
	{ ID id-LMF-UE-Measurement-ID		CRITICALITY reject	TYPE UE-Measurement-ID					PRESENCE mandatory}|
	{ ID id-RAN-UE-Measurement-ID		CRITICALITY reject	TYPE UE-Measurement-ID					PRESENCE mandatory}|
	{ ID id-E-CID-MeasurementResult		CRITICALITY ignore	TYPE E-CID-MeasurementResult			PRESENCE optional}|
	{ ID id-CriticalityDiagnostics		CRITICALITY ignore	TYPE CriticalityDiagnostics			PRESENCE optional}|
	{ ID id-Cell-Portion-ID				CRITICALITY ignore	TYPE Cell-Portion-ID					PRESENCE optional}|
	{ ID id-OtherRATMeasurementResult	CRITICALITY ignore	TYPE OtherRATMeasurementResult		PRESENCE optional}|
	{ ID id-WLANMeasurementResult		CRITICALITY ignore	TYPE WLANMeasurementResult			PRESENCE optional}, 
	...
}





E-CIDMeasurementInitiationFailure ::= SEQUENCE {
	protocolIEs						ProtocolIE-Container		{{E-CIDMeasurementInitiationFailure-IEs}}, 
	...
}


E-CIDMeasurementInitiationFailure-IEs NRPPA-PROTOCOL-IES ::= {
	{ ID id-LMF-UE-Measurement-ID		CRITICALITY reject	TYPE UE-Measurement-ID				PRESENCE mandatory}|
	{ ID id-Cause							CRITICALITY ignore	TYPE Cause							PRESENCE mandatory}|
	{ ID id-CriticalityDiagnostics		CRITICALITY ignore	TYPE CriticalityDiagnostics		PRESENCE optional}, 
	...
}





E-CIDMeasurementFailureIndication ::= SEQUENCE {
	protocolIEs						ProtocolIE-Container		{{E-CIDMeasurementFailureIndication-IEs}}, 
	...
}


E-CIDMeasurementFailureIndication-IEs NRPPA-PROTOCOL-IES ::= {
	{ ID id-LMF-UE-Measurement-ID		CRITICALITY reject	TYPE UE-Measurement-ID				PRESENCE mandatory}|
	{ ID id-RAN-UE-Measurement-ID		CRITICALITY reject	TYPE UE-Measurement-ID				PRESENCE mandatory}|
	{ ID id-Cause							CRITICALITY ignore	TYPE Cause							PRESENCE mandatory}, 
	...
}





E-CIDMeasurementReport ::= SEQUENCE {
	protocolIEs						ProtocolIE-Container		{{E-CIDMeasurementReport-IEs}}, 
	...
}


E-CIDMeasurementReport-IEs NRPPA-PROTOCOL-IES ::= {
	{ ID id-LMF-UE-Measurement-ID		CRITICALITY reject	TYPE UE-Measurement-ID				PRESENCE mandatory}|
	{ ID id-RAN-UE-Measurement-ID		CRITICALITY reject	TYPE UE-Measurement-ID				PRESENCE mandatory}|
	{ ID id-E-CID-MeasurementResult		CRITICALITY ignore	TYPE E-CID-MeasurementResult		PRESENCE mandatory}|
	{ ID id-Cell-Portion-ID				CRITICALITY ignore	TYPE Cell-Portion-ID				PRESENCE optional}, 
	...
}





E-CIDMeasurementTerminationCommand ::= SEQUENCE {
	protocolIEs						ProtocolIE-Container		{{E-CIDMeasurementTerminationCommand-IEs}}, 
	...
}


E-CIDMeasurementTerminationCommand-IEs NRPPA-PROTOCOL-IES ::= {
	{ ID id-LMF-UE-Measurement-ID		CRITICALITY reject	TYPE UE-Measurement-ID				PRESENCE mandatory}|
	{ ID id-RAN-UE-Measurement-ID		CRITICALITY reject	TYPE UE-Measurement-ID				PRESENCE mandatory}, 
	...
}





OTDOAInformationRequest ::= SEQUENCE {
	protocolIEs		ProtocolIE-Container	{{OTDOAInformationRequest-IEs}}, 
	...
}

OTDOAInformationRequest-IEs NRPPA-PROTOCOL-IES ::= {
	{ ID id-OTDOA-Information-Type-Group		CRITICALITY reject	TYPE OTDOA-Information-Type			PRESENCE mandatory}, 
	...
}

OTDOA-Information-Type ::= SEQUENCE (SIZE(1..maxnoOTDOAtypes)) OF ProtocolIE-Single-Container { { OTDOA-Information-TypeIEs} }

OTDOA-Information-TypeIEs	NRPPA-PROTOCOL-IES ::= {
	{ ID id-OTDOA-Information-Type-Item		CRITICALITY reject	TYPE OTDOA-Information-Type-Item	PRESENCE mandatory}, 
	...
}

OTDOA-Information-Type-Item ::= SEQUENCE {
	oTDOA-Information-Type-Item		OTDOA-Information-Item, 
	iE-Extensions					ProtocolExtensionContainer { { OTDOA-Information-Type-ItemExtIEs} } OPTIONAL, 
	...
}

OTDOA-Information-Type-ItemExtIEs NRPPA-PROTOCOL-EXTENSION ::= {
	...
}





OTDOAInformationResponse ::= SEQUENCE {
	protocolIEs		ProtocolIE-Container	{{OTDOAInformationResponse-IEs}}, 
	...
}

OTDOAInformationResponse-IEs NRPPA-PROTOCOL-IES ::= {
	{ ID id-OTDOACells						CRITICALITY ignore	TYPE OTDOACells					PRESENCE mandatory}|
	{ ID id-CriticalityDiagnostics			CRITICALITY ignore	TYPE CriticalityDiagnostics		PRESENCE optional}, 
	...
}





OTDOAInformationFailure ::= SEQUENCE {
	protocolIEs						ProtocolIE-Container		{{OTDOAInformationFailure-IEs}}, 
	...
}


OTDOAInformationFailure-IEs NRPPA-PROTOCOL-IES ::= {
	{ ID id-Cause							CRITICALITY ignore	TYPE Cause						PRESENCE mandatory}|
	{ ID id-CriticalityDiagnostics			CRITICALITY ignore	TYPE CriticalityDiagnostics		PRESENCE optional}, 
	...
}





AssistanceInformationControl ::= SEQUENCE {
	protocolIEs		ProtocolIE-Container	{{AssistanceInformationControl-IEs}}, 
	...
}

AssistanceInformationControl-IEs NRPPA-PROTOCOL-IES ::= {
	{ ID id-Assistance-Information	CRITICALITY reject	TYPE Assistance-Information		PRESENCE optional}|
	{ ID id-Broadcast				CRITICALITY reject	TYPE Broadcast					PRESENCE optional}|
	{ ID id-PositioningBroadcastCells				CRITICALITY reject	TYPE PositioningBroadcastCells					PRESENCE optional}, 
	...
}





AssistanceInformationFeedback ::= SEQUENCE {
	protocolIEs		ProtocolIE-Container	{{AssistanceInformationFeedback-IEs}}, 
	...
}

AssistanceInformationFeedback-IEs NRPPA-PROTOCOL-IES ::= {
	{ ID id-AssistanceInformationFailureList	CRITICALITY reject	TYPE AssistanceInformationFailureList	PRESENCE optional}|
	{ ID id-PositioningBroadcastCells				CRITICALITY reject	TYPE PositioningBroadcastCells					PRESENCE optional}|
	{ ID id-CriticalityDiagnostics				CRITICALITY ignore	TYPE CriticalityDiagnostics					PRESENCE optional}, 
	...
}





ErrorIndication ::= SEQUENCE {
	protocolIEs		ProtocolIE-Container	{{ErrorIndication-IEs}}, 
	...
}

ErrorIndication-IEs NRPPA-PROTOCOL-IES ::= {
	
	{ ID id-Cause							CRITICALITY ignore	TYPE Cause						PRESENCE optional}|
	{ ID id-CriticalityDiagnostics		CRITICALITY ignore	TYPE CriticalityDiagnostics	PRESENCE optional}, 
	...
}





PrivateMessage ::= SEQUENCE {
	privateIEs		PrivateIE-Container	{{PrivateMessage-IEs}}, 
	...
}

PrivateMessage-IEs NRPPA-PRIVATE-IES ::= {
	...
}





PositioningInformationRequest ::= SEQUENCE {
	protocolIEs		ProtocolIE-Container	{{PositioningInformationRequest-IEs}}, 
	...
}

PositioningInformationRequest-IEs NRPPA-PROTOCOL-IES ::= {
	{ ID id-RequestedSRSTransmissionCharacteristics	CRITICALITY ignore	TYPE RequestedSRSTransmissionCharacteristics	PRESENCE optional}, 
	...
}





PositioningInformationResponse ::= SEQUENCE {
	protocolIEs		ProtocolIE-Container	{{PositioningInformationResponse-IEs}}, 
	...
}

PositioningInformationResponse-IEs NRPPA-PROTOCOL-IES ::= {
	{ ID id-SRSConfiguration			CRITICALITY ignore	TYPE SRSConfiguration			PRESENCE optional}|
	{ ID id-SFNInitialisationTime		CRITICALITY ignore	TYPE SFNInitialisationTime		PRESENCE optional}|
	{ ID id-CriticalityDiagnostics		CRITICALITY ignore	TYPE CriticalityDiagnostics		PRESENCE optional}, 
	...
}





PositioningInformationFailure ::= SEQUENCE {
	protocolIEs						ProtocolIE-Container		{{PositioningInformationFailure-IEs}}, 
	...
}

PositioningInformationFailure-IEs NRPPA-PROTOCOL-IES ::= {
	{ ID id-Cause						CRITICALITY ignore	TYPE Cause						PRESENCE mandatory}|
	{ ID id-CriticalityDiagnostics		CRITICALITY ignore	TYPE CriticalityDiagnostics		PRESENCE optional}, 
	...
}





PositioningInformationUpdate ::= SEQUENCE {
	protocolIEs		ProtocolIE-Container	{{PositioningInformationUpdate-IEs}}, 
	...
}

PositioningInformationUpdate-IEs NRPPA-PROTOCOL-IES ::= {
	{ ID id-SRSConfiguration			CRITICALITY ignore	TYPE SRSConfiguration			PRESENCE optional}|
	{ ID id-SFNInitialisationTime		CRITICALITY ignore	TYPE SFNInitialisationTime		PRESENCE optional}, 
	...
}





MeasurementRequest ::= SEQUENCE {
	protocolIEs		ProtocolIE-Container	{{MeasurementRequest-IEs}}, 
	...
}

MeasurementRequest-IEs NRPPA-PROTOCOL-IES ::= {
	{ ID id-LMF-Measurement-ID			CRITICALITY reject	TYPE Measurement-ID				PRESENCE mandatory}|
	{ ID id-TRP-MeasurementRequestList		CRITICALITY reject	TYPE TRP-MeasurementRequestList PRESENCE mandatory}|
	{ ID id-ReportCharacteristics			CRITICALITY reject	TYPE ReportCharacteristics		PRESENCE mandatory}|
	{ ID id-MeasurementPeriodicity			CRITICALITY reject	TYPE MeasurementPeriodicity		PRESENCE conditional}|
	{ ID id-TRPMeasurementQuantities			CRITICALITY reject	TYPE TRPMeasurementQuantities		PRESENCE mandatory}|
	{ ID id-SRSConfiguration				CRITICALITY ignore	TYPE SRSConfiguration			PRESENCE optional}|
	{ ID id-SFNInitialisationTime			CRITICALITY ignore	TYPE SFNInitialisationTime		PRESENCE optional}|
	{ ID id-MeasurementBeamInfoRequest		CRITICALITY ignore	TYPE MeasurementBeamInfoRequest	PRESENCE optional}|
	{ ID id-SystemFrameNumber				CRITICALITY ignore	TYPE SystemFrameNumber			PRESENCE optional}|
	{ ID id-SlotNumber						CRITICALITY ignore	TYPE SlotNumber					PRESENCE optional}, 
	...
}





MeasurementResponse ::= SEQUENCE {
	protocolIEs		ProtocolIE-Container	{{MeasurementResponse-IEs}}, 
	...
}

MeasurementResponse-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}|
	{ ID id-TRP-MeasurementResponseList	CRITICALITY reject	TYPE TRP-MeasurementResponseList PRESENCE mandatory}|
	{ ID id-CriticalityDiagnostics		CRITICALITY ignore	TYPE CriticalityDiagnostics		PRESENCE optional}, 
	...
}





MeasurementFailure ::= SEQUENCE {
	protocolIEs						ProtocolIE-Container		{{MeasurementFailure-IEs}}, 
	...
}

MeasurementFailure-IEs NRPPA-PROTOCOL-IES ::= {
	{ ID id-LMF-Measurement-ID		CRITICALITY reject	TYPE Measurement-ID				PRESENCE mandatory}|
	{ ID id-Cause						CRITICALITY ignore	TYPE Cause						PRESENCE mandatory}|
	{ ID id-CriticalityDiagnostics		CRITICALITY ignore	TYPE CriticalityDiagnostics		PRESENCE optional}, 
	...
}





MeasurementReport ::= SEQUENCE {
	protocolIEs		ProtocolIE-Container	{{MeasurementReport-IEs}}, 
	...
}

MeasurementReport-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}|
	{ ID id-TRP-MeasurementReportList			CRITICALITY reject	TYPE TRP-MeasurementResponseList PRESENCE mandatory}, 
	
	...
}





MeasurementUpdate ::= SEQUENCE {
	protocolIEs		ProtocolIE-Container	{{MeasurementUpdate-IEs}}, 
	...
}

MeasurementUpdate-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}| 
	{ ID id-SRSConfiguration		CRITICALITY ignore	TYPE SRSConfiguration			PRESENCE optional}, 
	...
}





MeasurementAbort ::= SEQUENCE {
	protocolIEs		ProtocolIE-Container	{{MeasurementAbort-IEs}}, 
	...
}

MeasurementAbort-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}, 

	...
}





MeasurementFailureIndication ::= SEQUENCE {
	protocolIEs						ProtocolIE-Container		{{MeasurementFailureIndication-IEs}}, 
	...
}

MeasurementFailureIndication-IEs NRPPA-PROTOCOL-IES ::= {
	{ ID id-LMF-Measurement-ID		CRITICALITY reject	TYPE Measurement-ID				PRESENCE mandatory}|
	{ ID id-RAN-Measurement-ID		CRITICALITY reject	TYPE Measurement-ID				PRESENCE mandatory}|
	{ ID id-Cause					CRITICALITY ignore	TYPE Cause						PRESENCE mandatory}, 
	...
}





TRPInformationRequest ::= SEQUENCE {
	protocolIEs		ProtocolIE-Container	{{TRPInformationRequest-IEs}}, 
	...
}

TRPInformationRequest-IEs NRPPA-PROTOCOL-IES ::= {
	{ ID id-TRPList						CRITICALITY reject	TYPE TRPList				PRESENCE mandatory}|
	{ ID id-TRPInformationTypeList		CRITICALITY reject	TYPE TRPInformationTypeList	PRESENCE mandatory}, 	...
}





TRPInformationResponse ::= SEQUENCE {
	protocolIEs		ProtocolIE-Container	{{TRPInformationResponse-IEs}}, 
	...
}

TRPInformationResponse-IEs NRPPA-PROTOCOL-IES ::= {
	{ ID id-TRPInformationList				CRITICALITY ignore	TYPE TRPInformationList			PRESENCE mandatory}|
	{ ID id-CriticalityDiagnostics			CRITICALITY ignore	TYPE CriticalityDiagnostics		PRESENCE optional}, 
	...
}





TRPInformationFailure ::= SEQUENCE {
	protocolIEs						ProtocolIE-Container		{{TRPInformationFailure-IEs}}, 
	...
}

TRPInformationFailure-IEs NRPPA-PROTOCOL-IES ::= {
	{ ID id-Cause						CRITICALITY ignore	TYPE Cause						PRESENCE mandatory}|
	{ ID id-CriticalityDiagnostics		CRITICALITY ignore	TYPE CriticalityDiagnostics		PRESENCE optional}, 
	...
}





PositioningActivationRequest ::= SEQUENCE {
	protocolIEs			ProtocolIE-Container       { { PositioningActivationRequestIEs} }, 
	...
}

PositioningActivationRequestIEs NRPPA-PROTOCOL-IES ::= {
	{ ID id-SRSType					CRITICALITY reject	TYPE SRSType					PRESENCE mandatory	} |
	{ ID id-ActivationTime			CRITICALITY ignore	TYPE ActivationTime				PRESENCE optional	}, 
	...
} 

SRSType ::= CHOICE {
	semipersistentSRS				SemipersistentSRS, 
	aperiodicSRS					AperiodicSRS,  
	sRSType-extension				ProtocolIE-Single-Container { { SRSType-ExtIEs} }
}

SRSType-ExtIEs NRPPA-PROTOCOL-IES ::= {
	...
}

SemipersistentSRS ::= SEQUENCE {
	sRSResourceSetID			SRSResourceSetID, 
	iE-Extensions				ProtocolExtensionContainer { {SemipersistentSRS-ExtIEs} } OPTIONAL, 
	...
}

SemipersistentSRS-ExtIEs NRPPA-PROTOCOL-EXTENSION ::= {		
{ ID id-SRSSpatialRelation	CRITICALITY ignore	EXTENSION SRSSpatialRelation PRESENCE optional}, 
...
}

AperiodicSRS ::= SEQUENCE {
	aperiodic					ENUMERATED{true, ...}, 
	sRSResourceTrigger			SRSResourceTrigger OPTIONAL,  
	iE-Extensions				ProtocolExtensionContainer { {AperiodicSRS-ExtIEs} } OPTIONAL, 
	...
}

AperiodicSRS-ExtIEs NRPPA-PROTOCOL-EXTENSION ::= {
	...
}





PositioningActivationResponse ::= SEQUENCE {
	protocolIEs			ProtocolIE-Container       { { PositioningActivationResponseIEs} }, 
	...
}


PositioningActivationResponseIEs NRPPA-PROTOCOL-IES ::= {
	{ ID id-CriticalityDiagnostics		CRITICALITY ignore	TYPE CriticalityDiagnostics		PRESENCE optional }|
	{ ID id-SystemFrameNumber			CRITICALITY ignore	TYPE SystemFrameNumber			PRESENCE optional }|
	{ ID id-SlotNumber					CRITICALITY ignore	TYPE SlotNumber					PRESENCE optional }, 
	...
}





PositioningActivationFailure ::= SEQUENCE {
	protocolIEs			ProtocolIE-Container       { { PositioningActivationFailureIEs} }, 
	...
}

PositioningActivationFailureIEs NRPPA-PROTOCOL-IES ::= {
	{ ID id-Cause						CRITICALITY ignore	TYPE Cause						PRESENCE mandatory	}|
	{ ID id-CriticalityDiagnostics		CRITICALITY ignore	TYPE CriticalityDiagnostics		PRESENCE optional }, 
	...
}





PositioningDeactivation ::= SEQUENCE {
	protocolIEs			ProtocolIE-Container       { { PositioningDeactivationIEs} }, 
	...
}

PositioningDeactivationIEs NRPPA-PROTOCOL-IES ::= {
	{ ID id-AbortTransmission			CRITICALITY ignore	TYPE AbortTransmission		PRESENCE mandatory	} , 
	...
} 


END





NRPPA-IEs {
itu-t (0) identified-organization (4) etsi (0) mobileDomain (0) 
ngran-access (22) modules (3) nrppa (4) version1 (1) nrppa-IEs (2) }

DEFINITIONS AUTOMATIC TAGS ::= 

BEGIN

IMPORTS	
	
	id-MeasurementQuantities-Item, 
	id-GeographicalCoordinates, 
	id-ResultSS-RSRP, 
	id-ResultSS-RSRQ, 
	id-ResultCSI-RSRP, 
	id-ResultCSI-RSRQ, 
	id-AngleOfArrivalNR, 
	id-SRSSpatialRelation, 
	id-ResultNR, 
	id-ResultEUTRA, 
	maxCellinRANnode, 
	maxCellReport, 
	maxNrOfErrors, 
	maxNoMeas, 
	maxnoOTDOAtypes, 
	maxServCell, 
	id-OtherRATMeasurementQuantities-Item, 
	id-WLANMeasurementQuantities-Item, 
	maxGERANMeas, 
	maxUTRANMeas, 
	maxWLANchannels, 
	maxnoFreqHoppingBandsMinusOne, 
	id-TDD-Config-EUTRA-Item, 
	maxNrOfPosSImessage, 
	maxnoAssistInfoFailureListItems, 
	maxNrOfSegments, 
	maxNrOfPosSIBs, 
	maxnoPosMeas, 
	maxnoTRPs, 
	maxnoTRPInfoTypes, 
	maxNoOfMeasTRPs, 
	maxNoPath, 
	maxnoofAngleInfo, 
	maxnolcs-gcs-translation, 
	maxnoBcastCell, 
	maxnoSRSTriggerStates, 
	maxnoSpatialRelations, 
	maxNRMeas, 
	maxEUTRAMeas, 
	maxIndexesReport, 
	maxCellReportNR, 
	maxnoSRS-Carriers, 
	maxnoSCSs, 
	maxnoSRS-Resources, 
	maxnoSRS-PosResources, 
	maxnoSRS-ResourceSets, 
	maxnoSRS-ResourcePerSet, 
	maxnoSRS-PosResourceSets, 
	maxnoSRS-PosResourcePerSet, 
	maxPRS-ResourceSets, 
	maxPRS-ResourcesPerSet, 
	maxNoSSBs, 
	maxnoofPRSresourceSet, 
	maxnoofPRSresource



FROM NRPPA-Constants

	Criticality, 
	NRPPATransactionID, 
	ProcedureCode, 
	ProtocolIE-ID, 
	TriggeringMessage

FROM NRPPA-CommonDataTypes

	ProtocolExtensionContainer{}, 
	ProtocolIE-Single-Container{}, 
	
	NRPPA-PROTOCOL-EXTENSION, 
	NRPPA-PROTOCOL-IES

FROM NRPPA-Containers;

AbortTransmission ::= CHOICE {
	sRSResourceSetID		SRSResourceSetID, 
	releaseALL				NULL, 
	choice-extension							ProtocolIE-Single-Container { { AbortTransmission-ExtIEs } }
}

AbortTransmission-ExtIEs NRPPA-PROTOCOL-IES ::= {
	...
}

ActiveULBWP  ::= SEQUENCE {
	locationAndBandwidth		INTEGER (0..37949, ...), 
	subcarrierSpacing           ENUMERATED {kHz15,  kHz30,  kHz60,  kHz120, ...}, 
	cyclicPrefix				ENUMERATED {normal,  extended}, 
	txDirectCurrentLocation		INTEGER (0..3301, ...), 
	shift7dot5kHz				ENUMERATED {true,  ...} OPTIONAL, 
	sRSConfig					SRSConfig, 
	iE-Extensions				ProtocolExtensionContainer { { ActiveULBWP-ExtIEs} } OPTIONAL, 
	...
}

ActiveULBWP-ExtIEs NRPPA-PROTOCOL-EXTENSION ::= {
	...
}


ActivationTime ::= SFNInitialisationTime



AdditionalPathList ::= SEQUENCE (SIZE (1.. maxNoPath)) OF AdditionalPathListItem


AdditionalPathListItem ::= SEQUENCE {
	relativeTimeOfPath	RelativePathDelay, 
	pathQuality			TrpMeasurementQuality	OPTIONAL,   
	iE-Extensions		ProtocolExtensionContainer { { AdditionalPathListItem-ExtIEs} } OPTIONAL, 
	...
}

AdditionalPathListItem-ExtIEs NRPPA-PROTOCOL-EXTENSION ::= {
	...
}

AperiodicSRSResourceTriggerList ::= SEQUENCE (SIZE(1..maxnoSRSTriggerStates)) OF AperiodicSRSResourceTrigger

AperiodicSRSResourceTrigger ::= INTEGER (0..3,  ...)

Assistance-Information ::= SEQUENCE {
	systemInformation				SystemInformation, 
	iE-Extensions					ProtocolExtensionContainer { { Assistance-Information-ExtIEs} } OPTIONAL, 
	...
}

Assistance-Information-ExtIEs NRPPA-PROTOCOL-EXTENSION ::= {
	...
}

AssistanceInformationFailureList ::= SEQUENCE (SIZE (1..maxnoAssistInfoFailureListItems)) OF SEQUENCE {
	posSIB-Type						PosSIB-Type, 
	outcome							Outcome, 
	iE-Extensions					ProtocolExtensionContainer { {AssistanceInformationFailureList-ExtIEs} }	OPTIONAL, 
	...
}

AssistanceInformationFailureList-ExtIEs NRPPA-PROTOCOL-EXTENSION ::= {
	...
}

AssistanceInformationMetaData ::= SEQUENCE {
	encrypted			ENUMERATED {true,  ...}	OPTIONAL, 
	gNSSID				ENUMERATED {gps,  sbas,  qzss,  galileo,  glonass,  bds,  navic,  ...}	OPTIONAL, 
	sBASID				ENUMERATED {waas,  egnos,  msas,  gagan,  ...}					OPTIONAL, 	iE-Extensions		ProtocolExtensionContainer { { AssistanceInformationMetaData-ExtIEs} }	OPTIONAL, 
	...
}

AssistanceInformationMetaData-ExtIEs NRPPA-PROTOCOL-EXTENSION ::= {
	...
}

BandwidthSRS ::= CHOICE {
	fR1		ENUMERATED {kHz5,  kHz10,  kHz20,  kHz40,  kHz50,  kHz80,  kHz100,  ...}, 
	fR2		ENUMERATED {kHz50,  kHz100,  kHz200,  kHz400,  ...}, 
	...
}

BCCH ::= INTEGER (0..1023,  ...)

Broadcast ::= ENUMERATED {
	start, 
	stop, 
	...
}

BroadcastPeriodicity ::= ENUMERATED {
	ms80, 
	ms160, 
	ms320, 
	ms640, 
	ms1280, 
	ms2560, 
	ms5120, 
	...
}

PositioningBroadcastCells ::= SEQUENCE (SIZE (1..maxnoBcastCell)) OF NG-RAN-CGI 

BSSID ::= OCTET STRING (SIZE(6))

Cause ::= CHOICE {
	radioNetwork		CauseRadioNetwork, 
	protocol			CauseProtocol, 
	misc				CauseMisc, 
	cause-Extension	ProtocolIE-Single-Container {{ Cause-ExtensionIE }}
}

Cause-ExtensionIE NRPPA-PROTOCOL-IES ::= {
	...
}

CauseMisc ::= ENUMERATED {
	unspecified, 
	...
}

CauseProtocol ::= ENUMERATED {
	transfer-syntax-error, 
	abstract-syntax-error-reject, 
	abstract-syntax-error-ignore-and-notify, 
	message-not-compatible-with-receiver-state, 
	semantic-error, 
	unspecified, 
	abstract-syntax-error-falsely-constructed-message, 
	...
}

CauseRadioNetwork ::= ENUMERATED {
	unspecified, 
	requested-item-not-supported, 
	requested-item-temporarily-not-available, 
	...

}

Cell-Portion-ID ::= INTEGER (0..4095, ...)

CGI-EUTRA ::= SEQUENCE {
	pLMN-Identity				PLMN-Identity, 
	eUTRAcellIdentifier			EUTRACellIdentifier, 
	iE-Extensions				ProtocolExtensionContainer { {CGI-EUTRA-ExtIEs} } OPTIONAL, 
	...
}

CGI-EUTRA-ExtIEs NRPPA-PROTOCOL-EXTENSION ::= {
	...
}


CGI-NR ::= SEQUENCE {
	pLMN-Identity				PLMN-Identity, 
	nRcellIdentifier			NRCellIdentifier, 
	iE-Extensions				ProtocolExtensionContainer { {CGI-NR-ExtIEs} } OPTIONAL, 
	...
}

CGI-NR-ExtIEs NRPPA-PROTOCOL-EXTENSION ::= {
	...
}


CPLength-EUTRA ::= ENUMERATED {
	normal, 
	extended, 
	...
}

CriticalityDiagnostics ::= SEQUENCE {
	procedureCode					ProcedureCode					OPTIONAL, 
	triggeringMessage				TriggeringMessage				OPTIONAL, 
	procedureCriticality			Criticality					OPTIONAL, 
	nrppatransactionID				NRPPATransactionID				OPTIONAL, 
	iEsCriticalityDiagnostics		CriticalityDiagnostics-IE-List	OPTIONAL, 
	iE-Extensions					ProtocolExtensionContainer { {CriticalityDiagnostics-ExtIEs} }	OPTIONAL, 
	...
}


CriticalityDiagnostics-ExtIEs NRPPA-PROTOCOL-EXTENSION ::= {
	...
}

CriticalityDiagnostics-IE-List ::= SEQUENCE (SIZE (1..maxNrOfErrors)) OF
	SEQUENCE {
		iECriticality			Criticality, 
		iE-ID					ProtocolIE-ID, 
		typeOfError				TypeOfError, 
		iE-Extensions			ProtocolExtensionContainer { {CriticalityDiagnostics-IE-List-ExtIEs} } OPTIONAL, 
		...
}

CriticalityDiagnostics-IE-List-ExtIEs NRPPA-PROTOCOL-EXTENSION ::= {
	...
}

DL-Bandwidth-EUTRA ::= ENUMERATED {
	bw6, 
	bw15, 
	bw25, 
	bw50, 
	bw75, 
	bw100, 
	...
}

DL-PRS ::= SEQUENCE {
	prsid 					INTEGER (0..255), 
	dl-PRSResourceSetID		INTEGER (0..7), 
	dl-PRSResourceID		INTEGER (0..63)		OPTIONAL, 
	iE-Extensions			ProtocolExtensionContainer { {DL-PRS-ExtIEs} }	OPTIONAL, 
	...
}

DL-PRS-ExtIEs NRPPA-PROTOCOL-EXTENSION ::= {
	...
}

DL-PRSMutingPattern ::= CHOICE {
	two					BIT STRING (SIZE(2)), 
	four				BIT STRING (SIZE(4)), 
	six					BIT STRING (SIZE(6)), 
	eight				BIT STRING (SIZE(8)), 
	sixteen				BIT STRING (SIZE(16)), 
	thirty-two			BIT STRING (SIZE(32)), 
	choice-extension							ProtocolIE-Single-Container { { DL-PRSMutingPattern-ExtIEs } }
}

DL-PRSMutingPattern-ExtIEs NRPPA-PROTOCOL-IES ::= {
	...
}

DLPRSResourceCoordinates ::= SEQUENCE {
	listofDL-PRSResourceSetARP		SEQUENCE (SIZE(1.. maxPRS-ResourceSets)) OF DLPRSResourceSetARP, 
	iE-Extensions					ProtocolExtensionContainer { { DLPRSResourceCoordinates-ExtIEs } } OPTIONAL, 
	...
}

DLPRSResourceCoordinates-ExtIEs NRPPA-PROTOCOL-EXTENSION ::= {
	...
}

DLPRSResourceSetARP ::= SEQUENCE {
	dl-PRSResourceSetID				INTEGER (0..7), 
	dL-PRSResourceSetARPLocation	DL-PRSResourceSetARPLocation, 
	listofDL-PRSResourceARP			SEQUENCE (SIZE(1.. maxPRS-ResourcesPerSet)) OF DLPRSResourceARP, 
	iE-Extensions					ProtocolExtensionContainer { { DLPRSResourceSetARP-ExtIEs } } OPTIONAL, 
	...
}

DLPRSResourceSetARP-ExtIEs NRPPA-PROTOCOL-EXTENSION ::= {
	...
}


DL-PRSResourceSetARPLocation ::= CHOICE {
	relativeGeodeticLocation			RelativeGeodeticLocation, 
	relativeCartesianLocation			RelativeCartesianLocation, 
	choice-Extension					ProtocolIE-Single-Container { { DL-PRSResourceSetARPLocation-ExtIEs } }
}

DL-PRSResourceSetARPLocation-ExtIEs NRPPA-PROTOCOL-IES ::= {
	...
}


DLPRSResourceARP ::= SEQUENCE {
	dl-PRSResourceID			INTEGER (0..63), 
	dL-PRSResourceARPLocation	DL-PRSResourceARPLocation, 	
	iE-Extensions				ProtocolExtensionContainer { { DLPRSResourceARP-ExtIEs } } OPTIONAL, 
	...
}

DLPRSResourceARP-ExtIEs NRPPA-PROTOCOL-EXTENSION ::= {
	...
}

DL-PRSResourceARPLocation ::= CHOICE {
	relativeGeodeticLocation			RelativeGeodeticLocation, 
	relativeCartesianLocation			RelativeCartesianLocation, 
	choice-Extension					ProtocolIE-Single-Container { { DL-PRSResourceARPLocation-ExtIEs } }
}

DL-PRSResourceARPLocation-ExtIEs NRPPA-PROTOCOL-IES ::= {
	...
}

E-CID-MeasurementResult ::= SEQUENCE {
	servingCell-ID					NG-RAN-CGI, 
	servingCellTAC					TAC, 
	nG-RANAccessPointPosition		NG-RANAccessPointPosition	OPTIONAL, 
	measuredResults					MeasuredResults				OPTIONAL, 
	iE-Extensions					ProtocolExtensionContainer { { E-CID-MeasurementResult-ExtIEs} } OPTIONAL, 
	...
}

E-CID-MeasurementResult-ExtIEs NRPPA-PROTOCOL-EXTENSION ::= {
	{ ID id-GeographicalCoordinates	CRITICALITY ignore	EXTENSION GeographicalCoordinates PRESENCE optional}, 
	...
}

EUTRACellIdentifier ::= BIT STRING (SIZE (28))

EARFCN ::= INTEGER (0..262143,  ...)


GeographicalCoordinates ::= SEQUENCE {
	tRPPositionDefinitionType	TRPPositionDefinitionType, 
	dLPRSResourceCoordinates	DLPRSResourceCoordinates	OPTIONAL, 
	iE-Extensions				ProtocolExtensionContainer { { GeographicalCoordinates-ExtIEs } } OPTIONAL, 
	...
}

GeographicalCoordinates-ExtIEs NRPPA-PROTOCOL-EXTENSION ::= {
	...
}


GNB-RxTxTimeDiff ::= SEQUENCE {

	rxTxTimeDiff		GNBRxTxTimeDiffMeas, 
	additionalPathList	AdditionalPathList	OPTIONAL, 
	iE-Extensions		ProtocolExtensionContainer { { GNB-RxTxTimeDiff-ExtIEs} }	OPTIONAL, 
	...
}

GNB-RxTxTimeDiff-ExtIEs NRPPA-PROTOCOL-EXTENSION ::= {

	...
}


GNBRxTxTimeDiffMeas ::= CHOICE {
	k0			INTEGER (0.. 1970049), 
	k1			INTEGER (0.. 985025), 
	k2			INTEGER (0.. 492513), 
	k3			INTEGER (0.. 246257), 
	k4			INTEGER (0.. 123129), 
	k5			INTEGER (0.. 61565), 
	choice-extension		ProtocolIE-Single-Container { { GNBRxTxTimeDiffMeas-ExtIEs } } 
}

GNBRxTxTimeDiffMeas-ExtIEs		NRPPA-PROTOCOL-IES ::= {
	...
}

HESSID ::= OCTET STRING (SIZE(6))




LCG-to-GCS-TranslationItem::= SEQUENCE {
	alpha				INTEGER (0..359) 	OPTIONAL, 
	alphaFine			INTEGER (0..9) 		OPTIONAL, 
	beta				INTEGER (0..359)	OPTIONAL, 
	betaFine			INTEGER (0..9) 		OPTIONAL, 
	gamma				INTEGER (0..359) 	OPTIONAL, 
	gammaFine			INTEGER (0..9) 		OPTIONAL, 
	...
}


LocationUncertainty ::= SEQUENCE {
	horizontalUncertainty		INTEGER (0..255), 
	horizontalConfidence		INTEGER (0..100), 
	verticalUncertainty			INTEGER (0..255), 
	verticalConfidence			INTEGER (0..100), 
	iE-Extensions				ProtocolExtensionContainer { { LocationUncertainty-ExtIEs} } OPTIONAL, 
	...
}

LocationUncertainty-ExtIEs NRPPA-PROTOCOL-EXTENSION ::= {
	...
}

Measurement-ID ::= INTEGER (1.. 65536)

MeasurementBeamInfoRequest ::= ENUMERATED {true,  ...}

MeasurementBeamInfo ::= SEQUENCE {
	pRS-Resource-ID				PRS-Resource-ID		OPTIONAL, 
	pRS-Resource-Set-ID			PRS-Resource-Set-ID	OPTIONAL, 
	sSB-Index					SSB-Index			OPTIONAL, 
	iE-Extensions								ProtocolExtensionContainer { { MeasurementBeamInfo-ExtIEs} } OPTIONAL, 
	...
}

MeasurementBeamInfo-ExtIEs NRPPA-PROTOCOL-EXTENSION ::= {
	...
}


MeasurementPeriodicity ::= ENUMERATED {
	ms120, 
	ms240, 
	ms480, 
	ms640, 
	ms1024, 
	ms2048, 
	ms5120, 
	ms10240, 
	min1, 
	min6, 
	min12, 
	min30, 
	min60, 
	...
}

MeasurementQuantities ::= SEQUENCE (SIZE (1.. maxNoMeas)) OF ProtocolIE-Single-Container { {MeasurementQuantities-ItemIEs} }

MeasurementQuantities-ItemIEs NRPPA-PROTOCOL-IES ::= {
	{ ID id-MeasurementQuantities-Item	CRITICALITY reject	TYPE MeasurementQuantities-Item		PRESENCE mandatory}
}

MeasurementQuantities-Item ::= SEQUENCE {
	measurementQuantitiesValue					MeasurementQuantitiesValue, 
	iE-Extensions								ProtocolExtensionContainer { { MeasurementQuantitiesValue-ExtIEs} } OPTIONAL, 
	...
}

MeasurementQuantitiesValue-ExtIEs NRPPA-PROTOCOL-EXTENSION ::= {
	...
}

MeasurementQuantitiesValue ::= ENUMERATED {
	cell-ID, 
	angleOfArrival, 
	timingAdvanceType1, 
	timingAdvanceType2, 
	rSRP, 
	rSRQ, 
	... , 
	sS-RSRP, 
	sS-RSRQ, 
	cSI-RSRP, 
	cSI-RSRQ, 
	angleOfArrivalNR
}

MeasuredResults ::= SEQUENCE (SIZE (1.. maxNoMeas)) OF MeasuredResultsValue

MeasuredResultsValue ::= CHOICE { 
	valueAngleOfArrival-EUTRA				INTEGER (0..719), 
	valueTimingAdvanceType1-EUTRA			INTEGER (0..7690), 
	valueTimingAdvanceType2-EUTRA			INTEGER (0..7690), 
	resultRSRP-EUTRA						ResultRSRP-EUTRA, 
	resultRSRQ-EUTRA						ResultRSRQ-EUTRA, 
	measuredResultsValue-Extension			ProtocolIE-Single-Container {{ MeasuredResultsValue-ExtensionIE }}
}

MeasuredResultsValue-ExtensionIE NRPPA-PROTOCOL-IES ::= {
{ ID id-ResultSS-RSRP		CRITICALITY ignore	TYPE ResultSS-RSRP		PRESENCE mandatory	}|
	{ ID id-ResultSS-RSRQ		CRITICALITY ignore	TYPE ResultSS-RSRQ		PRESENCE mandatory	}|
	{ ID id-ResultCSI-RSRP		CRITICALITY ignore	TYPE ResultCSI-RSRP		PRESENCE mandatory	}|
	{ ID id-ResultCSI-RSRQ		CRITICALITY ignore	TYPE ResultCSI-RSRQ		PRESENCE mandatory	}|
	{ ID id-AngleOfArrivalNR	CRITICALITY ignore	TYPE UL-AoA				PRESENCE mandatory	}, 
	...
}

NarrowBandIndex ::= INTEGER (0..15, ...)

NG-RANAccessPointPosition ::= SEQUENCE {
	latitudeSign				ENUMERATED {north,  south}, 
	latitude					INTEGER (0..8388607), 
	longitude					INTEGER (-8388608..8388607), 
	directionOfAltitude			ENUMERATED {height,  depth}, 
	altitude					INTEGER (0..32767), 
	uncertaintySemi-major		INTEGER (0..127), 
	uncertaintySemi-minor		INTEGER (0..127), 
	orientationOfMajorAxis		INTEGER (0..179), 
	uncertaintyAltitude			INTEGER (0..127), 
	confidence					INTEGER (0..100), 
	iE-Extensions				ProtocolExtensionContainer { { NG-RANAccessPointPosition-ExtIEs} } OPTIONAL, 
	...
}

NG-RANAccessPointPosition-ExtIEs NRPPA-PROTOCOL-EXTENSION ::= {
	...
}

NGRANHighAccuracyAccessPointPosition ::= SEQUENCE {
	latitude					INTEGER (-2147483648.. 2147483647), 
	longitude					INTEGER (-2147483648.. 2147483647), 
	altitude					INTEGER (-64000..1280000), 
	uncertaintySemi-major		INTEGER (0..255), 
	uncertaintySemi-minor		INTEGER (0..255), 
	orientationOfMajorAxis		INTEGER (0..179), 
	horizontalConfidence		INTEGER (0..100), 
	uncertaintyAltitude			INTEGER (0..255), 
	verticalConfidence			INTEGER (0..100),  
	iE-Extensions				ProtocolExtensionContainer { { NGRANHighAccuracyAccessPointPosition-ExtIEs} } OPTIONAL, 
	...
}

NGRANHighAccuracyAccessPointPosition-ExtIEs NRPPA-PROTOCOL-EXTENSION ::= {
	...
}

NG-RAN-CGI ::= SEQUENCE {
	pLMN-Identity				PLMN-Identity, 
	nG-RANcell		NG-RANCell, 
	iE-Extensions				ProtocolExtensionContainer { {NG-RAN-CGI-ExtIEs} } OPTIONAL, 
	...
}

NG-RAN-CGI-ExtIEs NRPPA-PROTOCOL-EXTENSION ::= {
	...
}

NG-RANCell ::= CHOICE {
	eUTRA-CellID	EUTRACellIdentifier, 
	nR-CellID		NRCellIdentifier, 
	nG-RANCell-Extension			ProtocolIE-Single-Container {{ NG-RANCell-ExtensionIE }}
}

NG-RANCell-ExtensionIE NRPPA-PROTOCOL-IES ::= {
	...
}

NR-ARFCN ::= INTEGER (0..3279165)

NRCellIdentifier ::= BIT STRING (SIZE (36))

NR-PCI ::= INTEGER (0..1007)

NR-PRS-Beam-Information ::= SEQUENCE {
	nR-PRS-Beam-InformationList SEQUENCE (SIZE(1.. maxPRS-ResourceSets)) OF NR-PRS-Beam-InformationItem, 
	lCG-to-GCS-TranslationList SEQUENCE (SIZE(1..maxnolcs-gcs-translation)) OF LCG-to-GCS-TranslationItem, 
	iE-Extensions	ProtocolExtensionContainer { { NR-PRS-Beam-Information-IEs} } OPTIONAL, 
 	...
}

NR-PRS-Beam-Information-IEs NRPPA-PROTOCOL-EXTENSION ::= { 
 ...
}

NR-PRS-Beam-InformationItem ::= SEQUENCE {
	pRSresourceSetID 	INTEGER (0..7), 
	pRSAngleItem 		SEQUENCE (SIZE(1..maxPRS-ResourcesPerSet)) OF PRSAngleItem, 
	...
}

NumberOfAntennaPorts-EUTRA ::= ENUMERATED {
		n1-or-n2, 
		n4, 
		...
}

NumberOfDlFrames-EUTRA ::= ENUMERATED {
		sf1, 
		sf2, 
		sf4, 
		sf6, 
		...
}

NumberOfDlFrames-Extended-EUTRA ::= INTEGER (1..160, ...)

NumberOfFrequencyHoppingBands ::= ENUMERATED {
	twobands, 
	fourbands, 
	...
}

NZP-CSI-RS-ResourceID::= INTEGER  (0..191,  ...)

OTDOACells ::= SEQUENCE (SIZE (1.. maxCellinRANnode)) OF SEQUENCE {
	oTDOACellInfo					OTDOACell-Information, 
	iE-Extensions					ProtocolExtensionContainer { {OTDOACells-ExtIEs} } OPTIONAL, 
	...
}

OTDOACells-ExtIEs NRPPA-PROTOCOL-EXTENSION ::= {
	...
}

OTDOACell-Information ::= SEQUENCE (SIZE (1..maxnoOTDOAtypes)) OF OTDOACell-Information-Item

OTDOACell-Information-Item ::= CHOICE {
	pCI-EUTRA									PCI-EUTRA, 
	cGI-EUTRA									CGI-EUTRA, 
	tAC											TAC, 
	eARFCN										EARFCN, 
	pRS-Bandwidth-EUTRA							PRS-Bandwidth-EUTRA, 
	pRS-ConfigurationIndex-EUTRA				PRS-ConfigurationIndex-EUTRA,  
	cPLength-EUTRA								CPLength-EUTRA, 
	numberOfDlFrames-EUTRA						NumberOfDlFrames-EUTRA, 
	numberOfAntennaPorts-EUTRA					NumberOfAntennaPorts-EUTRA, 
	sFNInitialisationTime-EUTRA					SFNInitialisationTime-EUTRA, 
	nG-RANAccessPointPosition					NG-RANAccessPointPosition, 
	pRSMutingConfiguration-EUTRA				PRSMutingConfiguration-EUTRA, 
	prsid-EUTRA									PRS-ID-EUTRA, 
	tpid-EUTRA									TP-ID-EUTRA, 
	tpType-EUTRA								TP-Type-EUTRA, 
	numberOfDlFrames-Extended-EUTRA				NumberOfDlFrames-Extended-EUTRA, 
	crsCPlength-EUTRA							CPLength-EUTRA, 
	dL-Bandwidth-EUTRA							DL-Bandwidth-EUTRA, 
	pRSOccasionGroup-EUTRA						PRSOccasionGroup-EUTRA, 
	pRSFrequencyHoppingConfiguration-EUTRA		PRSFrequencyHoppingConfiguration-EUTRA, 
	oTDOACell-Information-Item-Extension		ProtocolIE-Single-Container {{ OTDOACell-Information-Item-ExtensionIE }}
}

OTDOACell-Information-Item-ExtensionIE NRPPA-PROTOCOL-IES ::= {
	{ ID id-TDD-Config-EUTRA-Item		CRITICALITY 	ignore	TYPE 	TDD-Config-EUTRA-Item		PRESENCE 	optional }, 
	...
}

OTDOA-Information-Item ::= ENUMERATED {
		pci, 
		cGI, 
		tac, 
		earfcn, 
		prsBandwidth, 
		prsConfigIndex, 
		cpLength, 
		noDlFrames, 
		noAntennaPorts, 
		sFNInitTime, 
		nG-RANAccessPointPosition, 
		prsmutingconfiguration, 
		prsid, 
		tpid, 
		tpType, 
		crsCPlength, 
		dlBandwidth,  
		multipleprsConfigurationsperCell, 
		prsOccasionGroup, 
		prsFrequencyHoppingConfiguration, 
		..., 
		tddConfig
}

OtherRATMeasurementQuantities ::= SEQUENCE (SIZE (0.. maxNoMeas)) OF ProtocolIE-Single-Container { {OtherRATMeasurementQuantities-ItemIEs} }

OtherRATMeasurementQuantities-ItemIEs NRPPA-PROTOCOL-IES ::= {
	{ ID id-OtherRATMeasurementQuantities-Item	CRITICALITY reject	TYPE OtherRATMeasurementQuantities-Item PRESENCE mandatory}}

OtherRATMeasurementQuantities-Item ::= SEQUENCE {
	otherRATMeasurementQuantitiesValue			OtherRATMeasurementQuantitiesValue, 
	iE-Extensions								ProtocolExtensionContainer { { OtherRATMeasurementQuantitiesValue-ExtIEs} } OPTIONAL, 
	...
}

OtherRATMeasurementQuantitiesValue-ExtIEs NRPPA-PROTOCOL-EXTENSION ::= {
	...
}

OtherRATMeasurementQuantitiesValue ::= ENUMERATED {
	geran, 
	utran, 
	... , 
	nR, 
	eUTRA
}

OtherRATMeasurementResult ::= SEQUENCE (SIZE (1.. maxNoMeas)) OF OtherRATMeasuredResultsValue

OtherRATMeasuredResultsValue ::= CHOICE {
	resultGERAN									ResultGERAN, 
	resultUTRAN									ResultUTRAN, 
	otherRATMeasuredResultsValue-Extension		ProtocolIE-Single-Container {{ OtherRATMeasuredResultsValue-ExtensionIE }}
}


OtherRATMeasuredResultsValue-ExtensionIE NRPPA-PROTOCOL-IES ::= {
	{ ID id-ResultNR		CRITICALITY 	ignore	TYPE 	ResultNR		PRESENCE 	mandatory }|
	{ ID id-ResultEUTRA		CRITICALITY 	ignore	TYPE 	ResultEUTRA		PRESENCE 	mandatory }, 
	...
}

Outcome ::= ENUMERATED {
		failed, 
		...
}

PathlossReferenceInformation ::= SEQUENCE {
	pathlossReferenceSignal					PathlossReferenceSignal, 
	iE-Extensions					ProtocolExtensionContainer { { PathlossReferenceInformation-ExtIEs } } OPTIONAL, 
	...
}

PathlossReferenceInformation-ExtIEs NRPPA-PROTOCOL-EXTENSION ::= {
	...
} 


PathlossReferenceSignal ::= CHOICE { 
	sSB-Reference					SSB, 
	dL-PRS-Reference				DL-PRS, 
	choice-Extension				ProtocolIE-Single-Container {{ PathlossReferenceSignal-ExtensionIE }}
}

PathlossReferenceSignal-ExtensionIE NRPPA-PROTOCOL-IES ::= {
	...
}


PCI-EUTRA ::= INTEGER (0..503,  ...)

PhysCellIDGERAN ::= INTEGER (0..63,  ...)

PhysCellIDUTRA-FDD ::= INTEGER (0..511,  ...)

PhysCellIDUTRA-TDD ::= INTEGER (0..127,  ...)

PLMN-Identity ::= OCTET STRING (SIZE(3))

PeriodicityList ::= SEQUENCE (SIZE (1.. maxnoSRS-ResourcePerSet)) OF PeriodicityItem

PeriodicityItem ::= ENUMERATED {ms0dot125,  ms0dot25,  ms0dot5,  ms0dot625,  ms1,  ms1dot25,  ms2,  ms2dot5,  ms4dot,  ms5,  ms8,  ms10,  ms16,  ms20,  ms32,  ms40,  ms64,  ms80m,  ms160,  ms320,  ms640m,  ms1280,  ms2560,  ms5120,  ms10240,  ...}


PosSIBs ::= SEQUENCE (SIZE (1.. maxNrOfPosSIBs)) OF SEQUENCE {
	posSIB-Type						PosSIB-Type, 
	posSIB-Segments					PosSIB-Segments, 
	assistanceInformationMetaData	AssistanceInformationMetaData	OPTIONAL, 
	broadcastPriority				INTEGER (1..16, ...)				OPTIONAL, 
	iE-Extensions					ProtocolExtensionContainer { { PosSIBs-ExtIEs} }	OPTIONAL, 
	...
}

PosSIBs-ExtIEs NRPPA-PROTOCOL-EXTENSION ::= {
	...
}

PosSIB-Segments ::= SEQUENCE (SIZE (1.. maxNrOfSegments)) OF SEQUENCE {
	assistanceDataSIBelement			OCTET STRING, 
	iE-Extensions						ProtocolExtensionContainer { { PosSIB-Segments-ExtIEs} }	OPTIONAL, 
	...
}

PosSIB-Segments-ExtIEs NRPPA-PROTOCOL-EXTENSION ::= {
	...
}

PosSIB-Type ::= ENUMERATED {
	posSibType1-1,  
	posSibType1-2,  
	posSibType1-3,  
	posSibType1-4,  
	posSibType1-5, 
	posSibType1-6,  
	posSibType1-7, 
	posSibType1-8,  
	posSibType2-1,  
	posSibType2-2,  
	posSibType2-3, 
	posSibType2-4,  
	posSibType2-5,  
	posSibType2-6,  
	posSibType2-7,  
	posSibType2-8, 
	posSibType2-9,  
	posSibType2-10,  
	posSibType2-11,  
	posSibType2-12,  
	posSibType2-13,  
	posSibType2-14,  
	posSibType2-15,  
	posSibType2-16, 
	posSibType2-17,  
	posSibType2-18,  
	posSibType2-19,  
	posSibType2-20,  
	posSibType2-21,  
	posSibType2-22,  
	posSibType2-23, 
	posSibType2-24, 
	posSibType2-25,  
	posSibType3-1,  
	posSibType4-1, 
	posSibType5-1, 
	posSibType6-1,   
	posSibType6-2, 
	posSibType6-3,   
	...
}

PosSRSResource-List ::= SEQUENCE (SIZE (1..maxnoSRS-PosResources)) OF PosSRSResource-Item

PosSRSResource-Item ::= SEQUENCE {
	srs-PosResourceId				SRSPosResourceID, 
	transmissionCombPos				TransmissionCombPos, 
	startPosition                   INTEGER (0..13), 
	nrofSymbols                     ENUMERATED {n1,  n2,  n4,  n8,  n12}, 
	freqDomainShift                 INTEGER (0..268), 
	c-SRS	                        INTEGER (0..63), 
	groupOrSequenceHopping          ENUMERATED { neither,  groupHopping,  sequenceHopping }, 
	resourceTypePos					ResourceTypePos, 
	sequenceId                      INTEGER (0.. 65535), 
	spatialRelationPos				SpatialRelationPos OPTIONAL, 
	iE-Extensions		ProtocolExtensionContainer { { PosSRSResource-Item-ExtIEs} }	OPTIONAL, 
	...
}

PosSRSResource-Item-ExtIEs NRPPA-PROTOCOL-EXTENSION ::= {
	...
}


PosSRSResourceSet-List ::= SEQUENCE (SIZE (1..maxnoSRS-PosResourceSets)) OF PosSRSResourceSet-Item

PosSRSResourceID-List ::= SEQUENCE (SIZE (1..maxnoSRS-PosResourcePerSet)) OF SRSPosResourceID
 

PosSRSResourceSet-Item ::= SEQUENCE {
	possrsResourceSetID				INTEGER(0..15), 
	possRSResourceID-List			PosSRSResourceID-List, 
	posresourceSetType				PosResourceSetType, 
	iE-Extensions		ProtocolExtensionContainer { { PosSRSResourceSet-Item-ExtIEs} }	OPTIONAL, 
	...
}

PosSRSResourceSet-Item-ExtIEs NRPPA-PROTOCOL-EXTENSION ::= {
	...
}

PosResourceSetType  ::= CHOICE {
	periodic			PosResourceSetTypePeriodic, 
	semi-persistent		PosResourceSetTypeSemi-persistent, 
	aperiodic			PosResourceSetTypeAperiodic, 
	choice-extension				ProtocolIE-Single-Container {{ PosResourceSetType-ExtIEs }}
}

PosResourceSetType-ExtIEs NRPPA-PROTOCOL-IES ::= {
	...
}

PosResourceSetTypePeriodic ::= SEQUENCE {
	posperiodicSet			ENUMERATED{true,  ...}, 
	iE-Extensions		ProtocolExtensionContainer { { PosResourceSetTypePeriodic-ExtIEs} }	OPTIONAL, 
	...
}

PosResourceSetTypePeriodic-ExtIEs NRPPA-PROTOCOL-EXTENSION ::= {
	...
}

PosResourceSetTypeSemi-persistent ::= SEQUENCE {
possemi-persistentSet	ENUMERATED{true,  ...}, 
	iE-Extensions		ProtocolExtensionContainer { { PosResourceSetTypeSemi-persistent-ExtIEs} }	OPTIONAL, 
	...
}

PosResourceSetTypeSemi-persistent-ExtIEs NRPPA-PROTOCOL-EXTENSION ::= {
	...
}

PosResourceSetTypeAperiodic ::= SEQUENCE {
	sRSResourceTrigger		 	INTEGER(1..3), 
	iE-Extensions				ProtocolExtensionContainer { { PosResourceSetTypeAperiodic-ExtIEs} }	OPTIONAL, 
	...
}

PosResourceSetTypeAperiodic-ExtIEs NRPPA-PROTOCOL-EXTENSION ::= {
	...
}

PRS-Bandwidth-EUTRA ::= ENUMERATED {
		bw6, 
		bw15, 
		bw25, 
		bw50, 
		bw75, 
		bw100, 
		...
}


PRSAngleItem  ::= SEQUENCE {
	pRSresourceAngleID		INTEGER (0..63), 
	nRPRSAzimuth			INTEGER (0..359), 
	nRPRSAzimuthFine		INTEGER (0..9) OPTIONAL, 
	nRPRSElevation			INTEGER (0..180) OPTIONAL, 
	nRPRSElevationFine		INTEGER (0..9) OPTIONAL, 
	...
}


PRSInformationPos  ::= SEQUENCE {
	pRS-IDPos					INTEGER(0..255) OPTIONAL, 	
	pRS-Resource-Set-IDPos		INTEGER(0..7), 
	pRS-Resource-IDPos			INTEGER(0..63), 
	iE-Extensions					ProtocolExtensionContainer { { PRSInformationPos-ExtIEs} } OPTIONAL, 
	...
}

PRSInformationPos-ExtIEs NRPPA-PROTOCOL-EXTENSION ::= {
	...
}

PRSConfiguration ::= SEQUENCE {
	pRSResourceSet-List				PRSResourceSet-List, 	
	iE-Extensions					ProtocolExtensionContainer { { PRSConfiguration-ExtIEs} } OPTIONAL, 
	...
}

PRSConfiguration-ExtIEs NRPPA-PROTOCOL-EXTENSION ::= {
	...
}


PRS-ConfigurationIndex-EUTRA ::= INTEGER (0..4095,  ...)

PRS-ID-EUTRA	::= INTEGER (0..4095,  ...)

PRSMutingConfiguration-EUTRA ::= CHOICE {
	two 												BIT STRING (SIZE (2)), 
	four 												BIT STRING (SIZE (4)), 
	eight 												BIT STRING (SIZE (8)), 
	sixteen 											BIT STRING (SIZE (16)), 
	thirty-two											BIT STRING (SIZE (32)), 
	sixty-four											BIT STRING (SIZE (64)), 
	one-hundred-and-twenty-eight						BIT STRING (SIZE (128)), 
	two-hundred-and-fifty-six							BIT STRING (SIZE (256)), 
	five-hundred-and-twelve								BIT STRING (SIZE (512)), 
	one-thousand-and-twenty-four						BIT STRING (SIZE (1024)), 
	pRSMutingConfiguration-EUTRA-Extension			ProtocolIE-Single-Container {{ PRSMutingConfiguration-EUTRA-ExtensionIE }}
}

PRSMutingConfiguration-EUTRA-ExtensionIE NRPPA-PROTOCOL-IES ::= {
	...
}

PRSOccasionGroup-EUTRA ::= ENUMERATED {
	og2, 
	og4, 
	og8, 
	og16, 
	og32, 
	og64, 
	og128, 
	...
}

PRSFrequencyHoppingConfiguration-EUTRA ::= SEQUENCE {
	noOfFreqHoppingBands		NumberOfFrequencyHoppingBands, 
	bandPositions				SEQUENCE(SIZE (1..maxnoFreqHoppingBandsMinusOne)) OF NarrowBandIndex, 
	iE-Extensions				ProtocolExtensionContainer { { PRSFrequencyHoppingConfiguration-EUTRA-Item-IEs} } OPTIONAL, 
	...
}

PRSFrequencyHoppingConfiguration-EUTRA-Item-IEs NRPPA-PROTOCOL-EXTENSION ::= {
	...
}

PRSMuting::= SEQUENCE {
	pRSMutingOption1			PRSMutingOption1, 
	pRSMutingOption2			PRSMutingOption2, 
	iE-Extensions					ProtocolExtensionContainer { { PRSMuting-ExtIEs} } OPTIONAL, 
	...
}
PRSMuting-ExtIEs NRPPA-PROTOCOL-EXTENSION ::= {
	...
}


PRSMutingOption1 ::= SEQUENCE {
	mutingPattern						DL-PRSMutingPattern, 
	mutingBitRepetitionFactor			ENUMERATED{n1, n2, n4, n8, ...}, 
	iE-Extensions					ProtocolExtensionContainer { { PRSMutingOption1-ExtIEs} } OPTIONAL, 
	...
}
PRSMutingOption1-ExtIEs NRPPA-PROTOCOL-EXTENSION ::= {
	...
}

PRSMutingOption2 ::= SEQUENCE {
	mutingPattern						DL-PRSMutingPattern, 
	iE-Extensions					ProtocolExtensionContainer { { PRSMutingOption2-ExtIEs} } OPTIONAL, 
	...
}
PRSMutingOption2-ExtIEs NRPPA-PROTOCOL-EXTENSION ::= {
	...
}

PRSResource-List::= SEQUENCE (SIZE (1..maxnoofPRSresource)) OF PRSResource-Item

PRSResource-Item  ::= SEQUENCE {
	pRSResourceID			INTEGER(0..63), 
	sequenceID				INTEGER(0..4095, ...), 
	rEOffset				INTEGER(0..11), 
	resourceSlotOffset		INTEGER(0..511, ...), 
	resourceSymbolOffset	INTEGER(0..12, ...), 
	qCLInfo					PRSResource-QCLInfo		OPTIONAL, 
	iE-Extensions					ProtocolExtensionContainer { { PRSResource-Item-ExtIEs} } OPTIONAL, 
	...
}
PRSResource-Item-ExtIEs NRPPA-PROTOCOL-EXTENSION ::= {
	...
}

PRSResource-QCLInfo  ::= SEQUENCE {
	qCLSourceSSBIndex		INTEGER(0..63) 					OPTIONAL, 
	qCLSourcePRSInfo		PRSResource-QCLSourcePRSInfo	OPTIONAL, 		
	iE-Extensions					ProtocolExtensionContainer { { PRSResource-QCLInfo-ExtIEs} } OPTIONAL, 
	...
}
PRSResource-QCLInfo-ExtIEs NRPPA-PROTOCOL-EXTENSION ::= {
	...
}

PRSResource-QCLSourcePRSInfo ::= SEQUENCE {
	qCLSourcePRSResourceSetID		INTEGER(0..7), 
	qCLSourcePRSResourceID 			INTEGER(0..63) OPTIONAL, 		
	iE-Extensions					ProtocolExtensionContainer { { PRSResource-QCLSourcePRSInfo-ExtIEs} } OPTIONAL, 
	...
}
PRSResource-QCLSourcePRSInfo-ExtIEs NRPPA-PROTOCOL-EXTENSION ::= {
	...
}



PRSResourceSet-List ::= SEQUENCE (SIZE (1..maxnoofPRSresourceSet)) OF PRSResourceSet-Item

PRSResourceSet-Item ::= SEQUENCE {
	pRSResourceSetID				INTEGER(0..7), 
	subcarrierSpacing				ENUMERATED{kHz15,  kHz30,  kHz60,  kHz120,  ...}, 
	pRSbandwidth					INTEGER(1..63), 
	startPRB						INTEGER(0..2176), 
	pointA							INTEGER (0..3279165), 
	combSize						ENUMERATED{n2,  n4,  n6,  n12,  ...}, 
	cPType							ENUMERATED{normal,  extended,  ...}, 
	resourceSetPeriodicity			ENUMERATED{n4, n5, n8, n10, n16, n20, n32, n40, n64, n80, n160, n320, n640, n1280, n2560, n5120, n10240, n20480, n40960,  n81920, ...}, 
	resourceSetSlotOffset			INTEGER(0..81919, ...), 
	resourceRepetitionFactor		ENUMERATED{rf1, rf2, rf4, rf6, rf8, rf16, rf32, ...}, 
	resourceTimeGap					ENUMERATED{tg1, tg2, tg4, tg8, tg16, tg32, ...}, 
	resourceNumberofSymbols			ENUMERATED{n2, n4, n6, n12, ...}, 
	pRSMuting						PRSMuting 		OPTIONAL, 
	pRSResourceTransmitPower		INTEGER(-60..50), 
	pRSResource-List				PRSResource-List, 	
	iE-Extensions					ProtocolExtensionContainer { { PRSResourceSet-Item-ExtIEs} } OPTIONAL, 
	...
}

PRSResourceSet-Item-ExtIEs NRPPA-PROTOCOL-EXTENSION ::= {
	...
}

PRS-Resource-ID ::= INTEGER (0..63)

PRS-Resource-Set-ID ::= INTEGER(0..7)

PRS-ID ::= INTEGER(0..255)


ReferenceSignal ::= CHOICE { 
	nZP-CSI-RS								NZP-CSI-RS-ResourceID, 
	sSB										SSB, 
	sRS										SRSResourceID, 
	positioningSRS							SRSPosResourceID, 
	dL-PRS									DL-PRS, 
	choice-Extension				ProtocolIE-Single-Container {{ReferenceSignal-ExtensionIE }}
}

ReferenceSignal-ExtensionIE NRPPA-PROTOCOL-IES ::= {
	...
}

ReferencePoint ::= CHOICE {
	relativeCoordinateID			CoordinateID, 
	referencePointCoordinate		NG-RANAccessPointPosition, 
	referencePointCoordinateHA		NGRANHighAccuracyAccessPointPosition, 
	choice-Extension				ProtocolIE-Single-Container { { ReferencePoint-ExtIEs} }
}

ReferencePoint-ExtIEs NRPPA-PROTOCOL-IES ::= {
	...
}

CoordinateID ::= INTEGER (0..511,  ...)
RelativeGeodeticLocation ::= SEQUENCE { 
	milli-Arc-SecondUnits		ENUMERATED {zerodot03,  zerodot3,  three,  ...}, 	heightUnits					ENUMERATED {mm,  cm,  m,  ...},  
	deltaLatitude				INTEGER (-1024.. 1023), 
	deltaLongitude				INTEGER (-1024.. 1023), 
	deltaHeight					INTEGER (-1024.. 1023), 
	locationUncertainty			LocationUncertainty, 
	iE-extensions						ProtocolExtensionContainer {{RelativeGeodeticLocation-ExtIEs }}	OPTIONAL, 
	...
}

RelativeGeodeticLocation-ExtIEs NRPPA-PROTOCOL-EXTENSION ::= {
	...
}


RelativeCartesianLocation ::= SEQUENCE {
	xYZunit						ENUMERATED {mm,  cm,  dm,  ...}, 
	xvalue						INTEGER (-65536..65535), 
	yvalue						INTEGER (-65536..65535), 
	zvalue						INTEGER (-32768..32767), 
	locationUncertainty			LocationUncertainty, 
	iE-Extensions				ProtocolExtensionContainer { { RelativeCartesianLocation-ExtIEs} } OPTIONAL, 
	...
}

RelativeCartesianLocation-ExtIEs NRPPA-PROTOCOL-EXTENSION ::= {
	...
}

RelativePathDelay ::= CHOICE {
	k0			INTEGER(0..16351, ...), 
	k1			INTEGER(0..8176, ...), 
	k2			INTEGER(0..4088, ...), 
	k3		INTEGER(0..2044, ...), 
	k4			INTEGER(0..1022, ...), 
	k5			INTEGER(0..511, ...), 
	...
}

ReportCharacteristics ::= ENUMERATED {
	onDemand, 
	periodic, 
	...
}

RequestedSRSTransmissionCharacteristics ::= SEQUENCE {
	numberOfTransmissions	INTEGER (0..500, ...)							OPTIONAL, 
	resourceType			ENUMERATED {periodic,  semi-persistent,  aperiodic,  ...}, 
	bandwidth				BandwidthSRS, 
	listOfSRSResourceSet	SEQUENCE (SIZE (1.. maxnoSRS-ResourceSets)) OF SRSResourceSet-Item	OPTIONAL, 
	sSBInformation			SSBInfo		OPTIONAL, 
	iE-Extensions			ProtocolExtensionContainer { { RequestedSRSTransmissionCharacteristics-ExtIEs} } OPTIONAL, 
	...
}

RequestedSRSTransmissionCharacteristics-ExtIEs NRPPA-PROTOCOL-EXTENSION ::= {
	...
}


SRSResourceSet-Item ::= SEQUENCE { 
	numberOfSRSResourcePerSet		INTEGER (1..16,  ...)			OPTIONAL, 
	periodicityList					PeriodicityList					OPTIONAL, 
	spatialRelationInformation		SpatialRelationInfo		OPTIONAL, 
	pathlossReferenceInformation	PathlossReferenceInformation	OPTIONAL, 
	...
}


ResourceSetType  ::= CHOICE {
	periodic			ResourceSetTypePeriodic, 
	semi-persistent		ResourceSetTypeSemi-persistent, 
	aperiodic			ResourceSetTypeAperiodic, 
	choice-extension				ProtocolIE-Single-Container {{ ResourceSetType-ExtIEs }}
}

ResourceSetType-ExtIEs NRPPA-PROTOCOL-IES ::= {
	...
}

ResourceSetTypePeriodic ::= SEQUENCE {
periodicSet			ENUMERATED{true,  ...}, 
	iE-Extensions		ProtocolExtensionContainer { { ResourceSetTypePeriodic-ExtIEs} }	OPTIONAL, 
	...
}

ResourceSetTypePeriodic-ExtIEs NRPPA-PROTOCOL-EXTENSION ::= {
	...
}

ResourceSetTypeSemi-persistent ::= SEQUENCE {
semi-persistentSet	ENUMERATED{true,  ...}, 
	iE-Extensions		ProtocolExtensionContainer { { ResourceSetTypeSemi-persistent-ExtIEs} }	OPTIONAL, 
	...
}

ResourceSetTypeSemi-persistent-ExtIEs NRPPA-PROTOCOL-EXTENSION ::= {
	...
}

ResourceSetTypeAperiodic ::= SEQUENCE {
	sRSResourceTrigger		 	INTEGER(1..3), 
	slotoffset					INTEGER(1..32), 
	iE-Extensions				ProtocolExtensionContainer { { ResourceSetTypeAperiodic-ExtIEs} }	OPTIONAL, 
	...
}

ResourceSetTypeAperiodic-ExtIEs NRPPA-PROTOCOL-EXTENSION ::= {
	...
}


ResourceType ::= CHOICE {
	periodic						ResourceTypePeriodic, 
	semi-persistent					ResourceTypeSemi-persistent, 
	aperiodic						ResourceTypeAperiodic, 
	choice-extension				ProtocolIE-Single-Container {{ ResourceType-ExtIEs }}
}

ResourceType-ExtIEs NRPPA-PROTOCOL-IES ::= {
	...
}
 
ResourceTypePeriodic ::= SEQUENCE {
	periodicity		 		  ENUMERATED{slot1,  slot2,  slot4,  slot5,  slot8,  slot10,  slot16,  slot20,  slot32,  slot40,  slot64,  slot80,  slot160,  slot320,  slot640,  slot1280,  slot2560,  ...}, 
	offset					INTEGER(0..2559,  ...), 
	iE-Extensions			ProtocolExtensionContainer { { ResourceTypePeriodic-ExtIEs} }	OPTIONAL, 
	...
}

ResourceTypePeriodic-ExtIEs NRPPA-PROTOCOL-EXTENSION ::= {
	...
}

ResourceTypeSemi-persistent ::= SEQUENCE {
	periodicity			ENUMERATED{slot1,  slot2,  slot4,  slot5,  slot8,  slot10,  slot16,  slot20,  slot32,  slot40,  slot64,  slot80,  slot160,  slot320,  slot640,  slot1280,  slot2560,  ...}, 
	offset				INTEGER(0..2559,  ...), 
	iE-Extensions		ProtocolExtensionContainer { { ResourceTypeSemi-persistent-ExtIEs} }	OPTIONAL, 
	...
}

ResourceTypeSemi-persistent-ExtIEs NRPPA-PROTOCOL-EXTENSION ::= {
	...
}

ResourceTypeAperiodic ::= SEQUENCE {
aperiodicResourceType	   ENUMERATED{true,  ...}, 
	iE-Extensions		ProtocolExtensionContainer { { ResourceTypeAperiodic-ExtIEs} }	OPTIONAL, 
	...
}

ResourceTypeAperiodic-ExtIEs NRPPA-PROTOCOL-EXTENSION ::= {
	...
}


ResourceTypePos ::= CHOICE {
	periodic			ResourceTypePeriodicPos, 
	semi-persistent		ResourceTypeSemi-persistentPos, 
	aperiodic			ResourceTypeAperiodicPos, 
	choice-extension				ProtocolIE-Single-Container {{ ResourceTypePos-ExtIEs }}
}

ResourceTypePos-ExtIEs NRPPA-PROTOCOL-IES ::= {
	...
}

ResourceTypePeriodicPos ::= SEQUENCE {
periodicity		   ENUMERATED{slot1,  slot2,  slot4,  slot5,  slot8,  slot10,  slot16,  slot20,  slot32,  slot40,  slot64,  slot80,  slot160,  slot320,  slot640,  slot1280,  slot2560,  slot5120,  slot10240,  slot20480,  slot40960,  slot81920,  ...}, 
offset				INTEGER(0..81919,  ...), 
	iE-Extensions		ProtocolExtensionContainer { { ResourceTypePeriodicPos-ExtIEs} }	OPTIONAL, 
	...
}

ResourceTypePeriodicPos-ExtIEs NRPPA-PROTOCOL-EXTENSION ::= {
	...
}

ResourceTypeSemi-persistentPos ::= SEQUENCE {
periodicity		   ENUMERATED{slot1,  slot2,  slot4,  slot5,  slot8,  slot10,  slot16,  slot20,  slot32,  slot40,  slot64,  slot80,  slot160,  slot320,  slot640,  slot1280,  slot2560,  slot5120,  slot10240,  slot20480,  slot40960,  slot81920,  ...}, 
offset				INTEGER(0..81919,  ...), 
	iE-Extensions		ProtocolExtensionContainer { { ResourceTypeSemi-persistentPos-ExtIEs} }	OPTIONAL, 
	...
}

ResourceTypeSemi-persistentPos-ExtIEs NRPPA-PROTOCOL-EXTENSION ::= {
	...
}

ResourceTypeAperiodicPos ::= SEQUENCE {
slotOffset          INTEGER (1..32), 
	iE-Extensions		ProtocolExtensionContainer { { ResourceTypeAperiodicPos-ExtIEs} }	OPTIONAL, 
	...
}

ResourceTypeAperiodicPos-ExtIEs NRPPA-PROTOCOL-EXTENSION ::= {
	...
}

ResultCSI-RSRP ::= SEQUENCE (SIZE (1.. maxCellReportNR)) OF ResultCSI-RSRP-Item

ResultCSI-RSRP-Item ::= SEQUENCE {
	nR-PCI					NR-PCI, 
	nR-ARFCN				NR-ARFCN, 
	nG-RAN-CGI				NG-RAN-CGI													OPTIONAL, 
	valueCSI-RSRP-Cell		ValueRSRP-NR												OPTIONAL, 
	cSI-RSRP-PerCSI-RS		ResultCSI-RSRP-PerCSI-RS									OPTIONAL, 
	iE-Extensions		ProtocolExtensionContainer { { ResultCSI-RSRP-Item-ExtIEs} }	OPTIONAL, 
	...
}

ResultCSI-RSRP-Item-ExtIEs NRPPA-PROTOCOL-EXTENSION ::= {
	...
}

ResultCSI-RSRP-PerCSI-RS ::= SEQUENCE (SIZE (1.. maxIndexesReport)) OF ResultCSI-RSRP-PerCSI-RS-Item

ResultCSI-RSRP-PerCSI-RS-Item ::= SEQUENCE {
	cSI-RS-Index		INTEGER (0..95), 
	valueCSI-RSRP		ValueRSRP-NR, 
	iE-Extensions		ProtocolExtensionContainer { { ResultCSI-RSRP-PerCSI-RS-Item-ExtIEs} }	OPTIONAL, 
	...
}

ResultCSI-RSRP-PerCSI-RS-Item-ExtIEs NRPPA-PROTOCOL-EXTENSION ::= {
	...
}

ResultCSI-RSRQ ::= SEQUENCE (SIZE (1.. maxCellReportNR)) OF ResultCSI-RSRQ-Item

ResultCSI-RSRQ-Item ::= SEQUENCE {
	nR-PCI				NR-PCI, 
	nR-ARFCN			NR-ARFCN, 
	nG-RAN-CGI			NG-RAN-CGI														OPTIONAL, 
	valueCSI-RSRQ-Cell	ValueRSRQ-NR													OPTIONAL, 
	cSI-RSRQ-PerCSI-RS		ResultCSI-RSRQ-PerCSI-RS									OPTIONAL, 
	iE-Extensions		ProtocolExtensionContainer { { ResultCSI-RSRQ-Item-ExtIEs} }	OPTIONAL, 
	...
}

ResultCSI-RSRQ-Item-ExtIEs NRPPA-PROTOCOL-EXTENSION ::= {
	...
}

ResultCSI-RSRQ-PerCSI-RS ::= SEQUENCE (SIZE (1.. maxIndexesReport)) OF ResultCSI-RSRQ-PerCSI-RS-Item

ResultCSI-RSRQ-PerCSI-RS-Item ::= SEQUENCE {
	cSI-RS-Index		INTEGER (0..95), 
	valueCSI-RSRQ		ValueRSRQ-NR, 
	iE-Extensions		ProtocolExtensionContainer { { ResultCSI-RSRQ-PerCSI-RS-Item-ExtIEs} }	OPTIONAL, 
	...
}

ResultCSI-RSRQ-PerCSI-RS-Item-ExtIEs NRPPA-PROTOCOL-EXTENSION ::= {
	...
}

ResultEUTRA ::= SEQUENCE (SIZE (1.. maxEUTRAMeas)) OF ResultEUTRA-Item

ResultEUTRA-Item ::= SEQUENCE {
	pCI-EUTRA			PCI-EUTRA, 
	eARFCN				EARFCN, 
	valueRSRP-EUTRA		ValueRSRP-EUTRA												OPTIONAL, 
	valueRSRQ-EUTRA		ValueRSRQ-EUTRA												OPTIONAL, 
	cGI-EUTRA			CGI-EUTRA													OPTIONAL, 
	iE-Extensions		ProtocolExtensionContainer { { ResultEUTRA-Item-ExtIEs} }	OPTIONAL, 
	...
}

ResultEUTRA-Item-ExtIEs NRPPA-PROTOCOL-EXTENSION ::= {
	...
}


ResultRSRP-EUTRA ::= SEQUENCE (SIZE (1.. maxCellReport)) OF ResultRSRP-EUTRA-Item

ResultRSRP-EUTRA-Item ::= SEQUENCE {
	pCI-EUTRA			PCI-EUTRA, 
	eARFCN				EARFCN, 
	cGI-EUTRA			CGI-EUTRA OPTIONAL, 
	valueRSRP-EUTRA		ValueRSRP-EUTRA, 
	iE-Extensions		ProtocolExtensionContainer { { ResultRSRP-EUTRA-Item-ExtIEs} } OPTIONAL, 
	...
}

ResultRSRP-EUTRA-Item-ExtIEs NRPPA-PROTOCOL-EXTENSION ::= {
	...
}

ResultRSRQ-EUTRA ::= SEQUENCE (SIZE (1.. maxCellReport)) OF ResultRSRQ-EUTRA-Item

ResultRSRQ-EUTRA-Item ::= SEQUENCE {
	pCI-EUTRA			PCI-EUTRA, 
	eARFCN				EARFCN, 
	cGI-UTRA			CGI-EUTRA OPTIONAL, 
	valueRSRQ-EUTRA		ValueRSRQ-EUTRA, 
	iE-Extensions		ProtocolExtensionContainer { { ResultRSRQ-EUTRA-Item-ExtIEs} } OPTIONAL, 
	...
}

ResultRSRQ-EUTRA-Item-ExtIEs NRPPA-PROTOCOL-EXTENSION ::= {
	...
}


ResultSS-RSRP ::= SEQUENCE (SIZE (1.. maxCellReportNR)) OF ResultSS-RSRP-Item

ResultSS-RSRP-Item ::= SEQUENCE {
	nR-PCI				NR-PCI, 
	nR-ARFCN			NR-ARFCN, 
	nG-RAN-CGI			NG-RAN-CGI													OPTIONAL, 
	valueSS-RSRP-Cell	ValueRSRP-NR												OPTIONAL, 
	sS-RSRP-PerSSB		ResultSS-RSRP-PerSSB										OPTIONAL, 
	iE-Extensions		ProtocolExtensionContainer { { ResultSS-RSRP-Item-ExtIEs} }	OPTIONAL, 
	...
}

ResultSS-RSRP-Item-ExtIEs NRPPA-PROTOCOL-EXTENSION ::= {
	...
}

ResultSS-RSRP-PerSSB ::= SEQUENCE (SIZE (1.. maxIndexesReport)) OF ResultSS-RSRP-PerSSB-Item

ResultSS-RSRP-PerSSB-Item ::= SEQUENCE {
	sSB-Index			INTEGER (0..63), 
	valueSS-RSRP		ValueRSRP-NR, 
	iE-Extensions		ProtocolExtensionContainer { { ResultSS-RSRP-PerSSB-Item-ExtIEs} }	OPTIONAL, 
	...
}

ResultSS-RSRP-PerSSB-Item-ExtIEs NRPPA-PROTOCOL-EXTENSION ::= {
	...
}

ResultSS-RSRQ ::= SEQUENCE (SIZE (1.. maxCellReportNR)) OF ResultSS-RSRQ-Item

ResultSS-RSRQ-Item ::= SEQUENCE {
	nR-PCI				NR-PCI, 
	nR-ARFCN			NR-ARFCN, 
	nG-RAN-CGI			NG-RAN-CGI													OPTIONAL, 
	valueSS-RSRQ-Cell	ValueRSRQ-NR												OPTIONAL, 
	sS-RSRQ-PerSSB		ResultSS-RSRQ-PerSSB										OPTIONAL, 
	iE-Extensions		ProtocolExtensionContainer { { ResultSS-RSRQ-Item-ExtIEs} }	OPTIONAL, 
	...
}

ResultSS-RSRQ-Item-ExtIEs NRPPA-PROTOCOL-EXTENSION ::= {
	...
}

ResultSS-RSRQ-PerSSB ::= SEQUENCE (SIZE (1.. maxIndexesReport)) OF ResultSS-RSRQ-PerSSB-Item

ResultSS-RSRQ-PerSSB-Item ::= SEQUENCE {
	sSB-Index			INTEGER (0..63), 
	valueSS-RSRQ		ValueRSRQ-NR, 
	iE-Extensions		ProtocolExtensionContainer { { ResultSS-RSRQ-PerSSB-Item-ExtIEs} }	OPTIONAL, 
	...
}

ResultSS-RSRQ-PerSSB-Item-ExtIEs NRPPA-PROTOCOL-EXTENSION ::= {
	...
}


ResultGERAN ::= SEQUENCE (SIZE (1.. maxGERANMeas)) OF ResultGERAN-Item

ResultGERAN-Item ::= SEQUENCE {
	bCCH				BCCH, 
	physCellIDGERAN		PhysCellIDGERAN, 
	rSSI				RSSI, 
	iE-Extensions		ProtocolExtensionContainer { { ResultGERAN-Item-ExtIEs} } OPTIONAL, 
	...
}

ResultGERAN-Item-ExtIEs NRPPA-PROTOCOL-EXTENSION ::= {
	...
}


ResultNR ::= SEQUENCE (SIZE (1.. maxNRMeas)) OF ResultNR-Item

ResultNR-Item ::= SEQUENCE {
	nR-PCI				NR-PCI, 
	nR-ARFCN			NR-ARFCN, 
	valueSS-RSRP-Cell	ValueRSRP-NR											OPTIONAL, 
	valueSS-RSRQ-Cell	ValueRSRQ-NR											OPTIONAL, 
	sS-RSRP-PerSSB		ResultSS-RSRP-PerSSB									OPTIONAL, 
	sS-RSRQ-PerSSB		ResultSS-RSRQ-PerSSB									OPTIONAL, 
	cGI-NR				CGI-NR													OPTIONAL, 
	iE-Extensions		ProtocolExtensionContainer { { ResultNR-Item-ExtIEs} }	OPTIONAL, 
	...
}

ResultNR-Item-ExtIEs NRPPA-PROTOCOL-EXTENSION ::= {
	...
}


ResultUTRAN ::= SEQUENCE (SIZE (1.. maxUTRANMeas)) OF ResultUTRAN-Item

ResultUTRAN-Item ::= SEQUENCE {
	uARFCN				UARFCN, 
	physCellIDUTRAN		CHOICE {
		physCellIDUTRA-FDD		PhysCellIDUTRA-FDD, 
		physCellIDUTRA-TDD		PhysCellIDUTRA-TDD
	}, 
	uTRA-RSCP			UTRA-RSCP OPTIONAL, 
	uTRA-EcN0			UTRA-EcN0 OPTIONAL, 
	iE-Extensions		ProtocolExtensionContainer { { ResultUTRAN-Item-ExtIEs} } OPTIONAL, 
	...
}

ResultUTRAN-Item-ExtIEs NRPPA-PROTOCOL-EXTENSION ::= {
	...
}

RSSI ::= INTEGER (0..63,  ...)

SCS-SpecificCarrier ::= SEQUENCE {
    offsetToCarrier                     INTEGER (0..2199, ...), 
    subcarrierSpacing                   ENUMERATED {kHz15,  kHz30,  kHz60,  kHz120, ...}, 
    carrierBandwidth                    INTEGER (0..275, ...), 
iE-Extensions					ProtocolExtensionContainer { { SCS-SpecificCarrier-ExtIEs } } OPTIONAL, 
	...
}

SCS-SpecificCarrier-ExtIEs NRPPA-PROTOCOL-EXTENSION ::= {
	...
} 


Search-window-information ::= SEQUENCE {
	expectedPropagationDelay		INTEGER (-3841..3841, ...), 
	delayUncertainty				INTEGER (1..246, ...), 
	iE-Extensions					ProtocolExtensionContainer { { Search-window-information-ExtIEs } } OPTIONAL, 
	...
}

Search-window-information-ExtIEs NRPPA-PROTOCOL-EXTENSION ::= {
	...
}


SFNInitialisationTime ::= BIT STRING (SIZE (64))


SFNInitialisationTime-EUTRA ::= BIT STRING (SIZE (64))

SlotNumber ::= INTEGER (0..79)

SpatialDirectionInformation ::= SEQUENCE {
	nR-PRS-Beam-Information			NR-PRS-Beam-Information, 
	iE-Extensions					ProtocolExtensionContainer { { SpatialDirectionInformation-ExtIEs } } OPTIONAL, 
	...
}

SpatialDirectionInformation-ExtIEs NRPPA-PROTOCOL-EXTENSION ::= {
	...
} 


SpatialRelationInfo ::= SEQUENCE {
	spatialRelationforResourceID					SpatialRelationforResourceID, 
	iE-Extensions		ProtocolExtensionContainer { {SpatialRelationInfo-ExtIEs} }	OPTIONAL, 
	...
}

SpatialRelationInfo-ExtIEs NRPPA-PROTOCOL-EXTENSION ::= {
	...
}


SpatialRelationforResourceID ::= SEQUENCE (SIZE(1..maxnoSpatialRelations)) OF SpatialRelationforResourceIDItem

SpatialRelationforResourceIDItem ::= SEQUENCE {
	referenceSignal		ReferenceSignal, 
	iE-Extensions		ProtocolExtensionContainer { {SpatialRelationforResourceIDItem-ExtIEs} }	OPTIONAL, 
	...
}

SpatialRelationforResourceIDItem-ExtIEs NRPPA-PROTOCOL-EXTENSION ::= {
	...
}


SpatialRelationPos ::= CHOICE {
	sSBPos					SSBPos, 
	pRSInformationPos		PRSInformationPos, 
	choice-extension				ProtocolIE-Single-Container {{ SpatialInformationPos-ExtIEs }}
}

SpatialInformationPos-ExtIEs NRPPA-PROTOCOL-IES ::= {
	...
}
 


SRSConfig  ::= SEQUENCE {
	sRSResource-List			SRSResource-List OPTIONAL, 
	posSRSResource-List			PosSRSResource-List OPTIONAL, 
	sRSResourceSet-List			SRSResourceSet-List OPTIONAL, 
	posSRSResourceSet-List		PosSRSResourceSet-List OPTIONAL, 
	iE-Extensions					ProtocolExtensionContainer { { SRSConfig-ExtIEs } } OPTIONAL, 
	...
}

SRSConfig-ExtIEs NRPPA-PROTOCOL-EXTENSION ::= {
	...
}

SRSCarrier-List ::= SEQUENCE (SIZE(1.. maxnoSRS-Carriers)) OF SRSCarrier-List-Item

SRSCarrier-List-Item ::= SEQUENCE {
	pointA							INTEGER (0..3279165, ...), 
	uplinkChannelBW-PerSCS-List		UplinkChannelBW-PerSCS-List, 
	activeULBWP						ActiveULBWP, 
	pCI								INTEGER (0..1007)		OPTIONAL, 
iE-Extensions					ProtocolExtensionContainer { { SRSCarrier-List-Item-ExtIEs } } OPTIONAL, 
	...
}

SRSCarrier-List-Item-ExtIEs NRPPA-PROTOCOL-EXTENSION ::= {
	...
}


SRSConfiguration ::= SEQUENCE {
	sRSCarrier-List		SRSCarrier-List, 	iE-Extensions			ProtocolExtensionContainer { { SRSConfiguration-ExtIEs } } OPTIONAL, 
	...
}

SRSConfiguration-ExtIEs NRPPA-PROTOCOL-EXTENSION ::= {
	...
} 

SRSPosResourceID ::= INTEGER (0..63,  ...)

SRSResource::= SEQUENCE {
	sRSResourceID                   SRSResourceID, 
	nrofSRS-Ports                   ENUMERATED {port1,  ports2,  ports4}, 
	transmissionComb				TransmissionComb, 
	startPosition                   INTEGER (0..13), 
    nrofSymbols                     ENUMERATED {n1,  n2,  n4}, 
    repetitionFactor              	ENUMERATED {n1,  n2,  n4}, 
    freqDomainPosition              INTEGER (0..67), 
	freqDomainShift                 INTEGER (0..268), 
	c-SRS                           INTEGER (0..63), 
	b-SRS                           INTEGER (0..3), 
	b-hop                           INTEGER (0..3), 
	groupOrSequenceHopping          ENUMERATED { neither,  groupHopping,  sequenceHopping }, 
	resourceType					ResourceType, 
	slotOffset						INTEGER (0..2559), 
	sequenceId                      INTEGER (0..1023), 
	iE-Extensions					ProtocolExtensionContainer { { SRSResource-ExtIEs } } OPTIONAL, 
	...
}

SRSResource-ExtIEs NRPPA-PROTOCOL-EXTENSION ::= {
	...
}

SRSResourceID ::= INTEGER (0..63,  ...)

SRSResource-List ::= SEQUENCE (SIZE (1..maxnoSRS-Resources)) OF SRSResource

SRSResourceSet-List ::= SEQUENCE (SIZE (1..maxnoSRS-ResourceSets)) OF SRSResourceSet 

SRSResourceID-List::= SEQUENCE (SIZE (1..maxnoSRS-ResourcePerSet)) OF SRSResourceID

SRSResourceSet::= SEQUENCE {
	sRSResourceSetID                INTEGER(0..15), 
	sRSResourceID-List				SRSResourceID-List, 
	resourceSetType					ResourceSetType, 
	iE-Extensions					ProtocolExtensionContainer { { SRSResourceSet-ExtIEs } } OPTIONAL, 
	...
}

SRSResourceSet-ExtIEs NRPPA-PROTOCOL-EXTENSION ::= {
	...
}

SRSResourceSetID ::= INTEGER (0..15,  ...)

SRSResourceTrigger ::= SEQUENCE {
	aperiodicSRSResourceTriggerList					AperiodicSRSResourceTriggerList, 
	iE-Extensions		ProtocolExtensionContainer { {SRSResourceTrigger-ExtIEs} }	OPTIONAL, 
	...
}

SRSResourceTrigger-ExtIEs NRPPA-PROTOCOL-EXTENSION ::= {
	...
}

SRSSpatialRelation ::= SEQUENCE {
	spatialRelationforResourceID				SpatialRelationforResourceID, 
	iE-Extensions		ProtocolExtensionContainer { {SRSSpatialRelation-ExtIEs} }	OPTIONAL, 
	...
}

SRSSpatialRelation-ExtIEs NRPPA-PROTOCOL-EXTENSION ::= {
	...
}


SSBInfo ::= SEQUENCE {
	listOfSSBInfo		SEQUENCE (SIZE (1..maxNoSSBs)) OF SSBInfoList, 
	iE-Extensions		ProtocolExtensionContainer { {SSBInfo-ExtIEs} }	OPTIONAL, 
	...
}

SSBInfo-ExtIEs NRPPA-PROTOCOL-EXTENSION ::= {
	...
}



SSBInfoList ::= SEQUENCE {
	pCI-NR				INTEGER  (0..1007), 
	sSB-Configuration	TF-Configuration, 
	iE-Extensions		ProtocolExtensionContainer { { SSBInfoList-ExtIEs} }	OPTIONAL, 
	...
}


SSBInfoList-ExtIEs NRPPA-PROTOCOL-EXTENSION ::= {
	...
}


SSB ::= SEQUENCE {
	pCI-NR				INTEGER  (0..1007), 
	ssb-index			INTEGER  (0..63)	OPTIONAL, 
	iE-Extensions		ProtocolExtensionContainer { {SSB-ExtIEs} }	OPTIONAL, 
	...
}

SSB-ExtIEs NRPPA-PROTOCOL-EXTENSION ::= {
	...
}


SSBPos ::= SEQUENCE {
	pCI-NR				INTEGER  (0..1007)	OPTIONAL, 
	ssb-index			INTEGER  (0..63), 
	iE-Extensions		ProtocolExtensionContainer { {SSBPos-ExtIEs} }	OPTIONAL, 
	...
}

SSBPos-ExtIEs NRPPA-PROTOCOL-EXTENSION ::= {
	...
}


SSBBurstPosition ::= CHOICE {
	shortBitmap			BIT STRING (SIZE(4)), 
	mediumBitmap		BIT STRING (SIZE(8)), 
	longBitmap			BIT STRING (SIZE(64)), 
	...
}


SSB-Index ::= INTEGER(0..63)


SSID ::= OCTET STRING (SIZE(1..32))

SystemFrameNumber ::= INTEGER (0..1023)

SystemInformation ::= SEQUENCE (SIZE (1.. maxNrOfPosSImessage)) OF SEQUENCE {
	broadcastPeriodicity				BroadcastPeriodicity, 
	posSIBs								PosSIBs, 
	iE-Extensions						ProtocolExtensionContainer { { SystemInformation-ExtIEs} }	OPTIONAL, 
	...
}

SystemInformation-ExtIEs NRPPA-PROTOCOL-EXTENSION ::= {
	...
}

TAC ::= OCTET STRING (SIZE(3))

TDD-Config-EUTRA-Item ::= SEQUENCE {
	subframeAssignment			ENUMERATED { sa0,  sa1,  sa2,  sa3,  sa4,  sa5,  sa6,  ... }, 
	iE-Extensions				ProtocolExtensionContainer { { TDD-Config-EUTRA-Item-Item-ExtIEs } } OPTIONAL, 
	...
}

TDD-Config-EUTRA-Item-Item-ExtIEs NRPPA-PROTOCOL-EXTENSION ::= {
	...
}


TF-Configuration ::= SEQUENCE {
	sSB-frequency				INTEGER (0..3279165), 
	sSB-subcarrier-spacing		ENUMERATED {kHz15,  kHz30,  kHz120,  kHz240,  ...}, 
	sSB-Transmit-power			INTEGER (-60..50), 
	sSB-periodicity				ENUMERATED {ms5,  ms10,  ms20,  ms40,  ms80,  ms160,  ...}, 
	sSB-half-frame-offset		INTEGER(0..1), 
	sSB-SFN-offset				INTEGER(0..15), 
	sSB-BurstPosition			SSBBurstPosition	OPTIONAL, 
	sFN-initialisation-time		SFNInitialisationTime	 OPTIONAL, 
	iE-Extensions		ProtocolExtensionContainer { { TF-Configuration-ExtIEs} }	OPTIONAL, 
	...
}

TF-Configuration-ExtIEs NRPPA-PROTOCOL-EXTENSION ::= {
	...
}


TimeStamp ::= SEQUENCE {
	systemFrameNumber		SystemFrameNumber, 
	slotIndex				TimeStampSlotIndex, 
	measurementTime			SFNInitialisationTime	OPTIONAL, 
	iE-Extension			ProtocolExtensionContainer { { TimeStamp-ExtIEs} }	OPTIONAL, 
	...
}

TimeStamp-ExtIEs NRPPA-PROTOCOL-EXTENSION ::= {
	...
}

TimeStampSlotIndex ::= CHOICE {
	sCS-15			INTEGER(0..9), 
	sCS-30			INTEGER(0..19), 
	sCS-60			INTEGER(0..39), 
	sCS-120			INTEGER(0..79), 
	choice-extension		ProtocolIE-Single-Container { { TimeStampSlotIndex-ExtIEs} }
}

TimeStampSlotIndex-ExtIEs NRPPA-PROTOCOL-IES ::= {
	...
}


TP-ID-EUTRA ::= INTEGER (0..4095,  ...)

TP-Type-EUTRA ::= ENUMERATED { prs-only-tp,  ... }


TransmissionComb ::= CHOICE {
	n2    SEQUENCE {
            combOffset-n2              INTEGER (0..1), 
            cyclicShift-n2             INTEGER (0..7)
        }, 
    n4    SEQUENCE {
            combOffset-n4              INTEGER (0..3), 
            cyclicShift-n4             INTEGER (0..11)
        }, 
	choice-extension				ProtocolIE-Single-Container { { TransmissionComb-ExtIEs} }
}
TransmissionComb-ExtIEs NRPPA-PROTOCOL-IES ::= {
	...
}

TransmissionCombPos ::= CHOICE {
	n2    SEQUENCE {
            combOffset-n2              INTEGER (0..1), 
            cyclicShift-n2             INTEGER (0..7)
        }, 
    n4    SEQUENCE {
            combOffset-n4              INTEGER (0..3), 
            cyclicShift-n4             INTEGER (0..11)
        }, 
    n8    SEQUENCE {
            combOffset-n8              INTEGER (0..7), 
            cyclicShift-n8             INTEGER (0..5)
        }, 

	choice-extension				ProtocolIE-Single-Container { { TransmissionCombPos-ExtIEs} }
}
TransmissionCombPos-ExtIEs NRPPA-PROTOCOL-IES ::= {
	...
}

TRPMeasurementQuantities ::= SEQUENCE (SIZE (1..maxnoPosMeas)) OF TRPMeasurementQuantitiesList-Item

TRPMeasurementQuantitiesList-Item ::= SEQUENCE {
	tRPMeasurementQuantities-Item		TRPMeasurementQuantities-Item, 
	timingReportingGranularityFactor	INTEGER (0..5) OPTIONAL, 
	iE-Extensions			ProtocolExtensionContainer {{ TRPMeasurementQuantitiesList-Item-ExtIEs}}		OPTIONAL, 
	...
}

TRPMeasurementQuantitiesList-Item-ExtIEs NRPPA-PROTOCOL-EXTENSION ::= {
	...
}

TRPMeasurementQuantities-Item ::= ENUMERATED {
	gNB-RxTxTimeDiff,  
	uL-SRS-RSRP,  
	uL-AoA,  
	uL-RTOA,  
	...
}

TrpMeasurementResult ::= SEQUENCE (SIZE (1.. maxnoPosMeas)) OF TrpMeasurementResultItem
TrpMeasurementResultItem ::= SEQUENCE {
	measuredResultsValue				TrpMeasuredResultsValue, 
	timeStamp							TimeStamp, 
	measurementQuality					TrpMeasurementQuality						OPTIONAL, 
	measurementBeamInfo					MeasurementBeamInfo				OPTIONAL, 
	iE-Extensions		ProtocolExtensionContainer {{TrpMeasurementResultItem-ExtIEs}}		OPTIONAL, 
	...
}

TrpMeasurementResultItem-ExtIEs NRPPA-PROTOCOL-EXTENSION ::= {
	...
}

TrpMeasuredResultsValue ::= CHOICE {
	uL-AngleOfArrival	UL-AoA, 
	uL-SRS-RSRP			UL-SRS-RSRP, 
	uL-RTOA				UL-RTOAMeasurement, 
	gNB-RxTxTimeDiff	GNB-RxTxTimeDiff, 
	choice-extension							ProtocolIE-Single-Container { { TrpMeasuredResultsValue-ExtIEs } }
}

TrpMeasuredResultsValue-ExtIEs NRPPA-PROTOCOL-IES ::= {
	...
}

TrpMeasurementQuality ::= CHOICE {
	timingMeasQuality		TrpMeasurementTimingQuality, 
	angleMeasQuality		TrpMeasurementAngleQuality, 
	choice-Extension		ProtocolIE-Single-Container {{ TrpMeasurementQuality-ExtIEs}}

}

TrpMeasurementQuality-ExtIEs NRPPA-PROTOCOL-IES ::= {
	...
}

TrpMeasurementTimingQuality ::= SEQUENCE {
	measurementQuality		INTEGER (0..31), 
	resolution				ENUMERATED {m0dot1,  m1,  m10,  m30,  ...}, 
	...
}


TrpMeasurementAngleQuality ::= SEQUENCE {
	azimuthQuality		INTEGER (0..255), 
	zenithQuality		INTEGER (0..255)	OPTIONAL, 
	resolution			ENUMERATED {deg0dot1,  ...}, 
	...
}


TRP-MeasurementRequestList ::= SEQUENCE (SIZE (1..maxNoOfMeasTRPs)) OF TRP-MeasurementRequestItem

TRP-MeasurementRequestItem ::= SEQUENCE {
	tRP-ID							TRP-ID,  
	search-window-information		Search-window-information	OPTIONAL,  
	iE-extensions					ProtocolExtensionContainer { { TRP-MeasurementRequestItem-ExtIEs } } OPTIONAL, 
	...
}

TRP-MeasurementRequestItem-ExtIEs NRPPA-PROTOCOL-EXTENSION ::= {
	...
}

TRP-MeasurementResponseList ::= SEQUENCE (SIZE (1..maxNoOfMeasTRPs)) OF TRP-MeasurementResponseItem

TRP-MeasurementResponseItem ::= SEQUENCE {
	tRP-ID							TRP-ID,  
	measurementResult				TrpMeasurementResult, 
	iE-extensions					ProtocolExtensionContainer { { TRP-MeasurementResponseItem-ExtIEs } } OPTIONAL, 
	...
}

TRP-MeasurementResponseItem-ExtIEs NRPPA-PROTOCOL-EXTENSION ::= {
	...
}

TRPInformationList ::= SEQUENCE (SIZE (1.. maxnoTRPs)) OF SEQUENCE {
	tRP-ID							TRP-ID, 
	tRPInformation					TRPInformation, 
	iE-Extensions					ProtocolExtensionContainer { {TRPInformation-ExtIEs} } OPTIONAL, 
	...
}

TRPInformation-ExtIEs NRPPA-PROTOCOL-EXTENSION ::= {
	...
}

TRPInformation ::= SEQUENCE (SIZE (1..maxnoTRPInfoTypes)) OF TRPInformationItem

TRPInformationItem ::= CHOICE {
	pCI-NR										INTEGER  (0..1007), 
	nG-RAN-CGI									NG-RAN-CGI, 
	aRFCN										INTEGER (0..3279165),  
	pRSConfiguration							PRSConfiguration, 
	sSBinformation								SSBInfo, 
	sFNInitialisationTime						SFNInitialisationTime, 
	spatialDirectionInformation					SpatialDirectionInformation, 
	geographicalCoordinates						GeographicalCoordinates, 
	choice-extension							ProtocolIE-Single-Container { { TRPInformationItem-ExtIEs } }
}

TRPInformationItem-ExtIEs NRPPA-PROTOCOL-IES ::= {
	...

}


TRPInformationTypeList ::= SEQUENCE (SIZE(1.. maxnoTRPInfoTypes)) OF TRPInformationTypeItem

TRPInformationTypeItem ::= ENUMERATED {
		nrPCI, 
		nG-RAN-CGI, 
		arfcn,  
		pRSConfig, 
		sSBInfo, 
		sFNInitTime, 
		spatialDirectInfo, 
		geoCoord, 

		...
}

TRPList ::= SEQUENCE (SIZE(1.. maxnoTRPs)) OF TRPItem

TRPItem ::= SEQUENCE {
		tRP-ID		TRP-ID, 
		...
}


TRP-ID ::= INTEGER (1.. maxnoTRPs,  ...)


TRPPositionDefinitionType ::= CHOICE {
	direct		TRPPositionDirect, 
	referenced	TRPPositionReferenced, 
	choice-extension							ProtocolIE-Single-Container { { TRPPositionDefinitionType-ExtIEs } }
}

TRPPositionDefinitionType-ExtIEs NRPPA-PROTOCOL-IES ::= {
	...
}


TRPPositionDirect ::= SEQUENCE {
	accuracy	TRPPositionDirectAccuracy, 
	iE-extensions		ProtocolExtensionContainer { { TRPPositionDirect-ExtIEs } }	OPTIONAL, 
	...
}

TRPPositionDirect-ExtIEs NRPPA-PROTOCOL-EXTENSION ::= {
	...
}

TRPPositionDirectAccuracy ::= CHOICE {
	tRPPosition			NG-RANAccessPointPosition						, 
	tRPHAposition		NGRANHighAccuracyAccessPointPosition	, 
	choice-extension			ProtocolIE-Single-Container { { TRPPositionDirectAccuracy-ExtIEs } }
}

TRPPositionDirectAccuracy-ExtIEs NRPPA-PROTOCOL-IES ::= {
	...
}


TRPPositionReferenced ::= SEQUENCE {
	referencePoint					ReferencePoint, 
	referencePointType				TRPReferencePointType, 
	iE-extensions							ProtocolExtensionContainer { { TRPPositionReferenced-ExtIEs } }	OPTIONAL, 
	...
}

TRPPositionReferenced-ExtIEs NRPPA-PROTOCOL-EXTENSION ::= {
	...
}

TRPReferencePointType ::= CHOICE {
	tRPPositionRelativeGeodetic			RelativeGeodeticLocation, 
	tRPPositionRelativeCartesian		RelativeCartesianLocation, 
	choice-extension							ProtocolIE-Single-Container { { TRPReferencePointType-ExtIEs } }
}

TRPReferencePointType-ExtIEs NRPPA-PROTOCOL-IES ::= {
	...
}


TypeOfError ::= ENUMERATED {
	not-understood, 
	missing, 
	...
}

UARFCN ::= INTEGER (0..16383,  ...)

UE-Measurement-ID ::= INTEGER (1..15,  ...,  256)

UTRA-EcN0 ::= INTEGER (0..49,  ...)

UTRA-RSCP ::= INTEGER (-5..91,  ...)


UL-AoA ::= SEQUENCE {
	azimuthAoA				INTEGER (0..3599), 
	zenithAoA				INTEGER (0..1799)	OPTIONAL, 
	angleCoordinateSystem	ENUMERATED {lCS,  gCS}	OPTIONAL, 
	iE-extensions			ProtocolExtensionContainer { { UL-AoA-ExtIEs } }	OPTIONAL, 
	...
}

UL-AoA-ExtIEs NRPPA-PROTOCOL-EXTENSION ::= {
	...
}


UL-RTOAMeasurement ::= SEQUENCE {
		uLRTOAmeas			ULRTOAMeas, 
		additionalPathList	AdditionalPathList	OPTIONAL, 
	...
}

ULRTOAMeas::= CHOICE {
	k0		INTEGER (0.. 1970049), 
	k1		INTEGER (0.. 985025), 
	k2		INTEGER (0.. 492513), 
	k3		INTEGER (0.. 246257), 
	k4		INTEGER (0.. 123129), 
	k5		INTEGER (0.. 61565), 	
	...
}


UL-SRS-RSRP ::= INTEGER (0..127)

UplinkChannelBW-PerSCS-List ::= SEQUENCE (SIZE (1..maxnoSCSs)) OF SCS-SpecificCarrier

ValueRSRP-EUTRA ::= INTEGER (0..97,  ...)

ValueRSRQ-EUTRA ::= INTEGER (0..34,  ...)

ValueRSRP-NR ::= INTEGER (0..127)

ValueRSRQ-NR ::= INTEGER (0..127)

WLANMeasurementQuantities ::= SEQUENCE (SIZE (0.. maxNoMeas)) OF ProtocolIE-Single-Container { {WLANMeasurementQuantities-ItemIEs} }

WLANMeasurementQuantities-ItemIEs NRPPA-PROTOCOL-IES ::= {
	{ ID id-WLANMeasurementQuantities-Item	CRITICALITY reject	TYPE WLANMeasurementQuantities-Item PRESENCE mandatory}}

WLANMeasurementQuantities-Item ::= SEQUENCE {
	wLANMeasurementQuantitiesValue			WLANMeasurementQuantitiesValue, 
	iE-Extensions							ProtocolExtensionContainer { { WLANMeasurementQuantitiesValue-ExtIEs} } OPTIONAL, 
	...
}

WLANMeasurementQuantitiesValue-ExtIEs NRPPA-PROTOCOL-EXTENSION ::= {
	...
}

WLANMeasurementQuantitiesValue ::= ENUMERATED {
	wlan, 
	...
}

WLANMeasurementResult ::= SEQUENCE (SIZE (1..maxNoMeas)) OF WLANMeasurementResult-Item

WLANMeasurementResult-Item ::= SEQUENCE {
	wLAN-RSSI			WLAN-RSSI, 
	sSID				SSID					OPTIONAL, 
	bSSID				BSSID					OPTIONAL, 
	hESSID				HESSID					OPTIONAL, 
	operatingClass		WLANOperatingClass		OPTIONAL, 
	countryCode			WLANCountryCode			OPTIONAL, 
	wLANChannelList		WLANChannelList			OPTIONAL, 
	wLANBand			WLANBand				OPTIONAL, 
	iE-Extensions		ProtocolExtensionContainer { { WLANMeasurementResult-Item-ExtIEs } }	OPTIONAL, 
	...
}

WLANMeasurementResult-Item-ExtIEs	NRPPA-PROTOCOL-EXTENSION ::= {
	...
}

WLAN-RSSI ::= INTEGER (0..141,  ...)

WLANBand ::= ENUMERATED {band2dot4,  band5,  ...}

WLANChannelList ::= SEQUENCE (SIZE (1..maxWLANchannels)) OF WLANChannel

WLANChannel ::= INTEGER (0..255)

WLANCountryCode ::= ENUMERATED {
	unitedStates, 
	europe, 
	japan, 
	global, 
	...
}

WLANOperatingClass ::= INTEGER (0..255)



END





NRPPA-CommonDataTypes {
itu-t (0) identified-organization (4) etsi (0) mobileDomain (0) 
ngran-access (22) modules (3) nrppa (4) version1 (1) nrppa-CommonDataTypes (3)}

DEFINITIONS AUTOMATIC TAGS ::= 

BEGIN





maxPrivateIEs 									INTEGER ::= 65535
maxProtocolExtensions 							INTEGER ::= 65535
maxProtocolIEs									INTEGER ::= 65535





Criticality		::= ENUMERATED { reject,  ignore,  notify }

NRPPATransactionID		::= INTEGER (0..32767)


Presence		::= ENUMERATED { optional,  conditional,  mandatory }

PrivateIE-ID	::= CHOICE {
	local			INTEGER (0.. maxPrivateIEs), 
	global			OBJECT IDENTIFIER
}

ProcedureCode		::= INTEGER (0..255)

ProtocolIE-ID		::= INTEGER (0..maxProtocolIEs)

TriggeringMessage	::= ENUMERATED { initiating-message,  successful-outcome,  unsuccessful-outcome}

END





NRPPA-Constants {
itu-t (0) identified-organization (4) etsi (0) mobileDomain (0) 
ngran-access (22) modules (3) nrppa (4) version1 (1) nrppa-Constants (4) }

DEFINITIONS AUTOMATIC TAGS ::= 

BEGIN

IMPORTS

	ProcedureCode, 
	ProtocolIE-ID
FROM NRPPA-CommonDataTypes;





id-errorIndication												ProcedureCode ::= 0
id-privateMessage												ProcedureCode ::= 1
id-e-CIDMeasurementInitiation									ProcedureCode ::= 2
id-e-CIDMeasurementFailureIndication							ProcedureCode ::= 3
id-e-CIDMeasurementReport										ProcedureCode ::= 4
id-e-CIDMeasurementTermination									ProcedureCode ::= 5
id-oTDOAInformationExchange										ProcedureCode ::= 6
id-assistanceInformationControl									ProcedureCode ::= 7
id-assistanceInformationFeedback								ProcedureCode ::= 8
id-positioningInformationExchange								ProcedureCode ::= 9
id-positioningInformationUpdate									ProcedureCode ::= 10
id-Measurement													ProcedureCode ::= 11
id-MeasurementReport											ProcedureCode ::= 12
id-MeasurementUpdate											ProcedureCode ::= 13
id-MeasurementAbort												ProcedureCode ::= 14
id-MeasurementFailureIndication									ProcedureCode ::= 15
id-tRPInformationExchange										ProcedureCode ::= 16
id-positioningActivation										ProcedureCode ::= 17
id-positioningDeactivation										ProcedureCode ::= 18





maxNrOfErrors								INTEGER ::= 256
maxCellinRANnode							INTEGER ::= 3840
maxIndexesReport							INTEGER ::= 64
maxNoMeas									INTEGER ::= 64
maxCellReport								INTEGER ::= 9
maxCellReportNR								INTEGER ::= 9
maxnoOTDOAtypes								INTEGER ::= 63
maxServCell									INTEGER ::= 5
maxEUTRAMeas								INTEGER ::= 8
maxGERANMeas								INTEGER ::= 8
maxNRMeas									INTEGER ::= 8
maxUTRANMeas								INTEGER ::= 8
maxWLANchannels								INTEGER ::= 16
maxnoFreqHoppingBandsMinusOne				INTEGER ::= 7
maxNoPath									INTEGER ::= 2
maxNrOfPosSImessage							INTEGER ::= 32
maxnoAssistInfoFailureListItems				INTEGER ::= 32
maxNrOfSegments								INTEGER ::= 64
maxNrOfPosSIBs								INTEGER ::= 32 
maxNoOfMeasTRPs								INTEGER ::= 64
maxnoTRPs									INTEGER ::= 65535
maxnoTRPInfoTypes							INTEGER ::= 64
maxnoofAngleInfo							INTEGER ::= 65535
maxnolcs-gcs-translation					INTEGER ::= 3
maxnoBcastCell								INTEGER ::= 16384
maxnoSRSTriggerStates						INTEGER ::= 3
maxnoSpatialRelations						INTEGER ::= 64
maxnoPosMeas								INTEGER ::= 16384
maxnoSRS-Carriers							INTEGER ::= 32
maxnoSCSs									INTEGER ::= 5
maxnoSRS-Resources							INTEGER ::= 64
maxnoSRS-PosResources						INTEGER ::= 64
maxnoSRS-ResourceSets						INTEGER ::= 16
maxnoSRS-ResourcePerSet						INTEGER ::= 16
maxnoSRS-PosResourceSets					INTEGER ::= 16
maxnoSRS-PosResourcePerSet					INTEGER ::= 16
maxPRS-ResourceSets							INTEGER ::= 2
maxPRS-ResourcesPerSet						INTEGER ::= 64
maxNoSSBs									INTEGER ::= 255
maxnoofPRSresourceSet						INTEGER ::= 8
maxnoofPRSresource							INTEGER ::= 64





id-Cause														ProtocolIE-ID ::= 0
id-CriticalityDiagnostics										ProtocolIE-ID ::= 1
id-LMF-UE-Measurement-ID										ProtocolIE-ID ::= 2
id-ReportCharacteristics										ProtocolIE-ID ::= 3
id-MeasurementPeriodicity										ProtocolIE-ID ::= 4
id-MeasurementQuantities										ProtocolIE-ID ::= 5
id-RAN-UE-Measurement-ID										ProtocolIE-ID ::= 6
id-E-CID-MeasurementResult										ProtocolIE-ID ::= 7
id-OTDOACells													ProtocolIE-ID ::= 8
id-OTDOA-Information-Type-Group									ProtocolIE-ID ::= 9
id-OTDOA-Information-Type-Item									ProtocolIE-ID ::= 10
id-MeasurementQuantities-Item									ProtocolIE-ID ::= 11
id-RequestedSRSTransmissionCharacteristics						ProtocolIE-ID ::= 12
id-Cell-Portion-ID												ProtocolIE-ID ::= 14
id-OtherRATMeasurementQuantities								ProtocolIE-ID ::= 15
id-OtherRATMeasurementQuantities-Item							ProtocolIE-ID ::= 16
id-OtherRATMeasurementResult									ProtocolIE-ID ::= 17
id-WLANMeasurementQuantities									ProtocolIE-ID ::= 19
id-WLANMeasurementQuantities-Item								ProtocolIE-ID ::= 20
id-WLANMeasurementResult										ProtocolIE-ID ::= 21
id-TDD-Config-EUTRA-Item										ProtocolIE-ID ::= 22
id-Assistance-Information										ProtocolIE-ID ::= 23
id-Broadcast													ProtocolIE-ID ::= 24
id-AssistanceInformationFailureList								ProtocolIE-ID ::= 25
id-SRSConfiguration												ProtocolIE-ID ::= 26
id-MeasurementResult											ProtocolIE-ID ::= 27
id-TRP-ID														ProtocolIE-ID ::= 28
id-TRPInformationTypeList										ProtocolIE-ID ::= 29
id-TRPInformationList											ProtocolIE-ID ::= 30
id-MeasurementBeamInfoRequest									ProtocolIE-ID ::= 31
id-ResultSS-RSRP												ProtocolIE-ID ::= 32
id-ResultSS-RSRQ												ProtocolIE-ID ::= 33
id-ResultCSI-RSRP												ProtocolIE-ID ::= 34
id-ResultCSI-RSRQ												ProtocolIE-ID ::= 35
id-AngleOfArrivalNR												ProtocolIE-ID ::= 36
id-GeographicalCoordinates										ProtocolIE-ID ::= 37
id-PositioningBroadcastCells									ProtocolIE-ID ::= 38
id-LMF-Measurement-ID											ProtocolIE-ID ::= 39
id-RAN-Measurement-ID											ProtocolIE-ID ::= 40
id-TRP-MeasurementRequestList									ProtocolIE-ID ::= 41
id-TRP-MeasurementResponseList									ProtocolIE-ID ::= 42
id-TRP-MeasurementReportList									ProtocolIE-ID ::= 43
id-SRSType														ProtocolIE-ID ::= 44
id-ActivationTime												ProtocolIE-ID ::= 45
id-SRSResourceSetID												ProtocolIE-ID ::= 46
id-TRPList														ProtocolIE-ID ::= 47
id-SRSSpatialRelation											ProtocolIE-ID ::= 48
id-SystemFrameNumber											ProtocolIE-ID ::= 49
id-SlotNumber													ProtocolIE-ID ::= 50
id-SRSResourceTrigger											ProtocolIE-ID ::= 51
id-TRPMeasurementQuantities										ProtocolIE-ID ::= 52
id-AbortTransmission											ProtocolIE-ID ::= 53 
id-SFNInitialisationTime										ProtocolIE-ID ::= 54
id-ResultNR														ProtocolIE-ID ::= 55
id-ResultEUTRA													ProtocolIE-ID ::= 56

END





NRPPA-Containers {
itu-t (0) identified-organization (4) etsi (0) mobileDomain (0) 
ngran-access (22) modules (3) nrppa (4) version1 (1) nrppa-Containers (5)}

DEFINITIONS AUTOMATIC TAGS ::= 

BEGIN





IMPORTS
	maxPrivateIEs, 
	maxProtocolExtensions, 
	maxProtocolIEs, 
	Criticality, 
	Presence, 
	PrivateIE-ID, 
	ProtocolIE-ID	
FROM NRPPA-CommonDataTypes;





NRPPA-PROTOCOL-IES ::= CLASS {
	&id					ProtocolIE-ID			UNIQUE, 
	&criticality		Criticality, 
	&Value, 
	&presence			Presence
}
WITH SYNTAX {
	ID					&id
	CRITICALITY			&criticality
	TYPE				&Value
	PRESENCE			&presence
}





NRPPA-PROTOCOL-EXTENSION ::= CLASS {
	&id					ProtocolIE-ID		UNIQUE, 
	&criticality		Criticality, 
	&Extension, 
	&presence			Presence
}
WITH SYNTAX {
	ID					&id
	CRITICALITY			&criticality
	EXTENSION			&Extension
	PRESENCE			&presence
}





NRPPA-PRIVATE-IES ::= CLASS {
	&id					PrivateIE-ID, 
	&criticality		Criticality, 
	&Value, 
	&presence			Presence
}
WITH SYNTAX {
	ID					&id
	CRITICALITY			&criticality
	TYPE				&Value
	PRESENCE			&presence
}





ProtocolIE-Container { NRPPA-PROTOCOL-IES : IEsSetParam} ::= 
	SEQUENCE (SIZE (0..maxProtocolIEs)) OF
	ProtocolIE-Field {{IEsSetParam}}

ProtocolIE-Single-Container { NRPPA-PROTOCOL-IES : IEsSetParam} ::= 
	ProtocolIE-Field {{IEsSetParam}}

ProtocolIE-Field { NRPPA-PROTOCOL-IES : IEsSetParam} ::= SEQUENCE {
	id				NRPPA-PROTOCOL-IES.&id				({IEsSetParam}), 
	criticality		NRPPA-PROTOCOL-IES.&criticality		({IEsSetParam}{@id}), 
	value			NRPPA-PROTOCOL-IES.&Value			({IEsSetParam}{@id})
}





ProtocolIE-ContainerList {INTEGER : lowerBound,  INTEGER : upperBound,  NRPPA-PROTOCOL-IES : IEsSetParam} ::=
	SEQUENCE (SIZE (lowerBound..upperBound)) OF
	ProtocolIE-Container {{IEsSetParam}}





ProtocolExtensionContainer { NRPPA-PROTOCOL-EXTENSION : ExtensionSetParam} ::= 
	SEQUENCE (SIZE (1..maxProtocolExtensions)) OF
	ProtocolExtensionField {{ExtensionSetParam}}

ProtocolExtensionField { NRPPA-PROTOCOL-EXTENSION : ExtensionSetParam} ::= SEQUENCE {
	id					NRPPA-PROTOCOL-EXTENSION.&id			({ExtensionSetParam}), 
	criticality			NRPPA-PROTOCOL-EXTENSION.&criticality	({ExtensionSetParam}{@id}), 
	extensionValue		NRPPA-PROTOCOL-EXTENSION.&Extension		({ExtensionSetParam}{@id})
}





PrivateIE-Container { NRPPA-PRIVATE-IES : IEsSetParam} ::= 
	SEQUENCE (SIZE (1..maxPrivateIEs)) OF
	PrivateIE-Field {{IEsSetParam}}

PrivateIE-Field { NRPPA-PRIVATE-IES : IEsSetParam} ::= SEQUENCE {
	id				NRPPA-PRIVATE-IES.&id				({IEsSetParam}), 
	criticality		NRPPA-PRIVATE-IES.&criticality		({IEsSetParam}{@id}), 
	value			NRPPA-PRIVATE-IES.&Value			({IEsSetParam}{@id})
}

END
