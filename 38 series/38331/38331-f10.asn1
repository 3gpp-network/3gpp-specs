NR-RRC-Definitions DEFINITIONS AUTOMATIC TAGS ::=

BEGIN





BCCH-BCH-Message ::= SEQUENCE {
	message											BCCH-BCH-MessageType
}

BCCH-BCH-MessageType ::= CHOICE {
	mib												MIB,
	messageClassExtension	SEQUENCE {}
}





DL-DCCH-Message ::= SEQUENCE {
	message											DL-DCCH-MessageType
}

DL-DCCH-MessageType ::= CHOICE {
	c1						CHOICE {
		rrcReconfiguration							RRCReconfiguration,
		spare15 NULL, spare14 NULL, spare13 NULL,
		spare12 NULL, spare11 NULL, spare10 NULL,
		spare9 NULL, spare8 NULL, spare7 NULL,
		spare6 NULL, spare5 NULL, spare4 NULL,
		spare3 NULL, spare2 NULL, spare1 NULL
	},
	messageClassExtension	SEQUENCE {}
}





UL-DCCH-Message ::= SEQUENCE {
	message											UL-DCCH-MessageType
}

UL-DCCH-MessageType ::= CHOICE {
	c1						CHOICE {
		measurementReport							MeasurementReport,
		rrcReconfigurationComplete					RRCReconfigurationComplete,
		spare14 NULL, spare13 NULL, spare12 NULL,
		spare11 NULL, spare10 NULL, spare9 NULL,
		spare8 NULL, spare7 NULL, spare6 NULL,
		spare5 NULL, spare4 NULL, spare3 NULL,
		spare2 NULL, spare1 NULL
	},
	messageClassExtension	SEQUENCE {}
}





MIB ::= SEQUENCE {
	
	
	systemFrameNumber					BIT STRING (SIZE (6)),

	
	
	
	subCarrierSpacingCommon				ENUMERATED {scs15or60, scs30or120},

	
	
	
	ssb-SubcarrierOffset				INTEGER (0..15),

	
	dmrs-TypeA-Position					ENUMERATED {pos2, pos3},

	
	
	pdcch-ConfigSIB1					INTEGER (0..255), 

	
	cellBarred							ENUMERATED {barred, notBarred}, 
	
	
	
	intraFreqReselection				ENUMERATED {allowed, notAllowed},
	spare								BIT STRING (SIZE (1))
}





MeasurementReport ::=				SEQUENCE {
	criticalExtensions					CHOICE {
		measurementReport							MeasurementReport-IEs,
		criticalExtensionsFuture					SEQUENCE {}
	}
}

MeasurementReport-IEs ::=		SEQUENCE {
	measResults						MeasResults,

	lateNonCriticalExtension				OCTET STRING															OPTIONAL,
	nonCriticalExtension					SEQUENCE{}																OPTIONAL
}





RRCReconfiguration ::= 				SEQUENCE {
	rrc-TransactionIdentifier			RRC-TransactionIdentifier,
	criticalExtensions					CHOICE {
		rrcReconfiguration					RRCReconfiguration-IEs,
		criticalExtensionsFuture			SEQUENCE {}
	}
}

RRCReconfiguration-IEs ::= 			SEQUENCE {
	
    
	
	radioBearerConfig						RadioBearerConfig 														OPTIONAL,  -- Need M

	
	secondaryCellGroup						OCTET STRING (CONTAINING CellGroupConfig)								OPTIONAL,  -- Need M

	measConfig								MeasConfig																OPTIONAL,  -- Need M

	lateNonCriticalExtension				OCTET STRING															OPTIONAL,
	nonCriticalExtension					SEQUENCE {}																OPTIONAL 
}





RRCReconfigurationComplete ::= 			SEQUENCE {
	rrc-TransactionIdentifier				RRC-TransactionIdentifier,
	criticalExtensions						CHOICE {
		rrcReconfigurationComplete				RRCReconfigurationComplete-IEs,
		criticalExtensionsFuture				SEQUENCE {}
	}
}

RRCReconfigurationComplete-IEs ::= SEQUENCE {
	lateNonCriticalExtension				OCTET STRING															OPTIONAL,
	nonCriticalExtension					SEQUENCE {}																OPTIONAL 
}





SIB1 ::=		SEQUENCE {

	

	
	
	frequencyOffsetSSB				ENUMERATED {khz-5, khz5}																OPTIONAL,	 -- Need R

	
	ssb-PositionsInBurst				SEQUENCE {
		
		inOneGroup							BIT STRING (SIZE (8)),
		
		groupPresence						BIT STRING (SIZE (8))										OPTIONAL  -- Cond above6GHzOnly
	},

	
	ssb-PeriodicityServingCell			ENUMERATED {ms5, ms10, ms20, ms40, ms80, ms160, spare1, spare2},

	
	
	ss-PBCH-BlockPower					INTEGER (-60..50),

	uplinkConfigCommon						UplinkConfigCommon											OPTIONAL,
	
	supplementaryUplink					SEQUENCE {
		uplinkConfigCommon					UplinkConfigCommon											OPTIONAL 
		
	}																									OPTIONAL,  -- Cond SUL

	tdd-UL-DL-Configuration				TDD-UL-DL-ConfigCommon											OPTIONAL,  -- Cond TDD
	tdd-UL-DL-configurationCommon2		TDD-UL-DL-ConfigCommon											OPTIONAL,  -- Cond TDD

	pdcch-ConfigCommon					PDCCH-ConfigCommon												OPTIONAL,
	pucch-ConfigCommon					PUCCH-ConfigCommon												OPTIONAL,

	lateNonCriticalExtension				OCTET STRING															OPTIONAL,
	nonCriticalExtension					SEQUENCE{}																OPTIONAL 
}





SetupRelease { ElementTypeParam } ::= CHOICE {
	release			NULL,
	setup			ElementTypeParam
}





AdditionalSpectrumEmission ::=				INTEGER (0..7)





Alpha ::=						ENUMERATED {alpha0, alpha04, alpha05, alpha06, alpha07, alpha08, alpha09, alpha1}





ARFCN-ValueNR ::=				INTEGER (0..3279165)







BWP ::= 					SEQUENCE {
	
	
	
	
	locationAndBandwidth			INTEGER (0..37949),
	
	
	
	
	
	subcarrierSpacing				SubcarrierSpacing,
	
	
	
	cyclicPrefix					ENUMERATED { extended }														OPTIONAL	 -- Need R
}

BWP-Uplink ::= 			SEQUENCE {
	
	
	
	
	
	
	
	bwp-Id								BWP-Id,
	bwp-Common							BWP-UplinkCommon														OPTIONAL,	 -- Need M
	bwp-Dedicated						BWP-UplinkDedicated														OPTIONAL,	 -- Need M
	...
}

BWP-UplinkCommon ::=				SEQUENCE {
	genericParameters					BWP,
	
	
	rach-ConfigCommon					SetupRelease { RACH-ConfigCommon }										OPTIONAL, 	 -- Need M
	
	pusch-ConfigCommon					SetupRelease { PUSCH-ConfigCommon }										OPTIONAL, 	 -- Need M
	
	
	pucch-ConfigCommon					SetupRelease { PUCCH-ConfigCommon }										OPTIONAL, 	 -- Need M
	...
}

BWP-UplinkDedicated ::= 	SEQUENCE {
	
	
	pucch-Config						SetupRelease { PUCCH-Config }											OPTIONAL, 	 -- Need M
	
	
	
	pusch-Config						SetupRelease { PUSCH-Config }											OPTIONAL, 	 -- Need M
	
	configuredGrantConfig				SetupRelease { ConfiguredGrantConfig }									OPTIONAL, 	 -- Need M
	
	srs-Config							SetupRelease { SRS-Config }												OPTIONAL, 	 -- Need M
	
	beamFailureRecoveryConfig			SetupRelease { BeamFailureRecoveryConfig }								OPTIONAL,	 -- Need M
	...
}


BWP-Downlink ::= 					SEQUENCE {
	
	
	
	
	
	
	
	bwp-Id								BWP-Id,
	bwp-Common							BWP-DownlinkCommon														OPTIONAL,	 -- Need M
	bwp-Dedicated						BWP-DownlinkDedicated													OPTIONAL,	 -- Need M
	...
}


BWP-DownlinkCommon ::=				SEQUENCE {
	genericParameters					BWP,
	pdcch-ConfigCommon					SetupRelease { PDCCH-ConfigCommon }										OPTIONAL,	 -- Need M
	pdsch-ConfigCommon					SetupRelease { PDSCH-ConfigCommon }										OPTIONAL,	 -- Need M
	...
}

BWP-DownlinkDedicated ::= 			SEQUENCE {
	pdcch-Config						SetupRelease { PDCCH-Config }											OPTIONAL,	 -- Need M
	pdsch-Config						SetupRelease { PDSCH-Config }											OPTIONAL,	 -- Need M 
	sps-Config							SetupRelease { SPS-Config }												OPTIONAL, 	 -- Need M
	radioLinkMonitoringConfig			SetupRelease { RadioLinkMonitoringConfig }								OPTIONAL,	 -- Need M
	...
}






BWP-Id ::=							INTEGER (0..maxNrofBWPs)





BeamFailureRecoveryConfig ::= 		SEQUENCE {
	rootSequenceIndex-BFR				INTEGER (0..137)															OPTIONAL,	 --	Need M
	
	rach-ConfigBFR						RACH-ConfigGeneric															OPTIONAL,	 --	Need M
	
	
	
	
	candidateBeamThreshold		RSRP-Range																			OPTIONAL,	 --	Need M
	
	candidateBeamRSList					SEQUENCE (SIZE(1..maxNrofCandidateBeams)) OF PRACH-ResourceDedicatedBFR		OPTIONAL,	 --	Need M
	
	ra-ssb-OccasionMaskIndex			INTEGER (0..15)																OPTIONAL, 	 --	Need M
	
	
	recoveryControlResourceSetId		ControlResourceSetId														OPTIONAL	,	 -- Need S
	
	recoverySearchSpaceId				SearchSpaceId																OPTIONAL,	 -- Need S
	...
}

PRACH-ResourceDedicatedBFR ::= 		CHOICE {
	ssb									BFR-SSB-Resource,
	csi-RS								BFR-CSIRS-Resource
}

BFR-SSB-Resource ::= 			SEQUENCE {
	
	ssb								SSB-Index,
	
	ra-PreambleIndex				INTEGER (0..63),
	...
}

BFR-CSIRS-Resource ::=			SEQUENCE {
	
	
	csi-RS							NZP-CSI-RS-ResourceId,
	
	
	
	
	ra-PreambleIndex				INTEGER (0..63)																	OPTIONAL,	 -- Need R
	...
}






CellGroupConfig	::= 						SEQUENCE {
	cellGroupId									CellGroupId,

	
	rlc-BearerToAddModList 						SEQUENCE (SIZE(1..maxLC-ID)) OF RLC-Bearer-Config				OPTIONAL,    -- Need N
	rlc-BearerToReleaseList						SEQUENCE (SIZE(1..maxLC-ID)) OF LogicalChannelIdentity			OPTIONAL,    -- Need N

	
	mac-CellGroupConfig							MAC-CellGroupConfig												OPTIONAL,	 -- Need M
	physicalCellGroupConfig						PhysicalCellGroupConfig											OPTIONAL,	 -- Need M

	
	spCellConfig								SpCellConfig													OPTIONAL, 	 -- Need M
	sCellToAddModList							SEQUENCE (SIZE (1..maxNrofSCells)) OF SCellConfig				OPTIONAL,	 -- Need N
	
	sCellToReleaseList							SEQUENCE (SIZE (1..maxNrofSCells)) OF SCellIndex				OPTIONAL,	 -- Need N
	...
}




CellGroupId ::=									INTEGER (0.. maxSecondaryCellGroups)


RLC-Bearer-Config ::=								SEQUENCE {
	
	logicalChannelIdentity						LogicalChannelIdentity,

	
	
	
	
	servedRadioBearer							CHOICE {
		srb-Identity                           SRB-Identity,
		drb-Identity                           DRB-Identity
	}																											OPTIONAL,	 -- Cond LCH-SetupOnly

	reestablishRLC								ENUMERATED {true}												OPTIONAL, 	 -- Need N
	rlc-Config									RLC-Config														OPTIONAL,	 -- Cond LCH-Setup

	mac-LogicalChannelConfig					LogicalChannelConfig											OPTIONAL,	 -- Cond LCH-Setup
	...	
}

LogicalChannelIdentity ::= 					INTEGER (1..maxLC-ID)


PhysicalCellGroupConfig ::=					SEQUENCE {
	
	
	
	
	harq-ACK-SpatialBundlingPUCCH				ENUMERATED {true}												OPTIONAL,	 -- Need R

	
	
	
	
	harq-ACK-SpatialBundlingPUSCH				ENUMERATED {true}												OPTIONAL,	 -- Need R
	
	p-NR										P-Max															OPTIONAL,	 -- Need R
	
	
	pdsch-HARQ-ACK-Codebook						ENUMERATED {semiStatic, dynamic},
	
	tpc-SRS-RNTI								RNTI-Value														OPTIONAL,	 -- Need R
	
	tpc-PUCCH-RNTI								RNTI-Value														OPTIONAL,	 -- Need R
	
	tpc-PUSCH-RNTI	RNTI-Value																					OPTIONAL, -- Need R
	...
}



SpCellConfig ::=						SEQUENCE {
	
	servCellIndex						ServCellIndex															OPTIONAL,	 -- Cond SCG
	
	reconfigurationWithSync 			ReconfigurationWithSync 												OPTIONAL,	 -- Cond ReconfWithSync
	rlf-TimersAndConstants				SetupRelease { RLF-TimersAndConstants }									OPTIONAL,	 -- Need M
	rlmInSyncOutOfSyncThreshold         INTEGER (0..1)                         									OPTIONAL,	 -- Need M
	spCellConfigDedicated				ServingCellConfig														OPTIONAL,	 -- Need M
	...
}

ReconfigurationWithSync ::=			SEQUENCE {
	spCellConfigCommon					ServingCellConfigCommon													OPTIONAL,	 -- Need M
	newUE-Identity						RNTI-Value,
	t304								ENUMERATED {ms50, ms100, ms150, ms200, ms500, ms1000, ms2000, ms10000},
		rach-ConfigDedicated				CHOICE {
			uplink								RACH-ConfigDedicated,
			supplementaryUplink					RACH-ConfigDedicated
	}																											OPTIONAL,	 -- Need N
	...
}			

SCellConfig ::=						SEQUENCE {
	sCellIndex							SCellIndex,
	sCellConfigCommon					ServingCellConfigCommon													OPTIONAL,	 -- Cond SCellAdd
	sCellConfigDedicated				ServingCellConfig														OPTIONAL,	 -- Cond SCellAddMod
	...
}




CodebookConfig ::= 									SEQUENCE {
	
	
	codebookType 										CHOICE {
		type1 												SEQUENCE {
			subType										CHOICE {
				typeI-SinglePanel									SEQUENCE {
					nrOfAntennaPorts									CHOICE {
						two													SEQUENCE {
							
							
							twoTX-CodebookSubsetRestriction						BIT STRING (SIZE (6))
						},
						moreThanTwo											SEQUENCE {
							
							
							
							n1-n2												CHOICE {
								two-one-TypeI-SinglePanel-Restriction				BIT STRING (SIZE (8)),
								two-two-TypeI-SinglePanel-Restriction				BIT STRING (SIZE (64)),
								four-one-TypeI-SinglePanel-Restriction				BIT STRING (SIZE (16)),
								three-two-TypeI-SinglePanel-Restriction				BIT STRING (SIZE (96)),
								six-one-TypeI-SinglePanel-Restriction				BIT STRING (SIZE (24)),
								four-two-TypeI-SinglePanel-Restriction				BIT STRING (SIZE (128)),
								eight-one-TypeI-SinglePanel-Restriction				BIT STRING (SIZE (32)),
								four-three-TypeI-SinglePanel-Restriction			BIT STRING (SIZE (192)),
								six-two-TypeI-SinglePanel-Restriction				BIT STRING (SIZE (192)),
								twelve-one-TypeI-SinglePanel-Restriction			BIT STRING (SIZE (48)),
								four-four-TypeI-SinglePanel-Restriction				BIT STRING (SIZE (256)),
								eight-two-TypeI-SinglePanel-Restriction				BIT STRING (SIZE (256)),
								sixteen-one-TypeI-SinglePanel-Restriction			BIT STRING (SIZE (64))
							},
							
							
							typeI-SinglePanel-codebookSubsetRestriction-i2		BIT STRING (SIZE (16))	OPTIONAL
						}
					},
					
					
					typeI-SinglePanel-ri-Restriction					BIT STRING (SIZE (8))
				}, 
				typeI-MultiPanel									SEQUENCE {
					
					
					ng-n1-n2												CHOICE {
						two-two-one-TypeI-MultiPanel-Restriction				BIT STRING (SIZE (8)),
						two-four-one-TypeI-MultiPanel-Restriction				BIT STRING (SIZE (32)),
						four-two-one-TypeI-MultiPanel-Restriction				BIT STRING (SIZE (32)),
						two-two-two-TypeI-MultiPanel-Restriction				BIT STRING (SIZE (128)),
						two-eight-one-TypeI-MultiPanel-Restriction				BIT STRING (SIZE (64)),
						four-four-one-TypeI-MultiPanel-Restriction				BIT STRING (SIZE (64)),
						two-four-two-TypeI-MultiPanel-Restriction				BIT STRING (SIZE (256)),
						four-two-two-TypeI-MultiPanel-Restriction				BIT STRING (SIZE (256))
					},
					
					
					ri-Restriction							BIT STRING (SIZE (4))
				}
			},
			
			codebookMode										INTEGER (1..2)

		},
		type2									SEQUENCE {
			subType									CHOICE {
				typeII									SEQUENCE {
					
					
					
					
					
					n1-n2-codebookSubsetRestriction			CHOICE {
						two-one									BIT STRING (SIZE (16)),
						two-two									BIT STRING (SIZE (139)),
						four-one								BIT STRING (SIZE (32)),
						three-two								BIT STRING (SIZE (59)),
						six-one									BIT STRING (SIZE (49)),
						four-two								BIT STRING (SIZE (75)),
						eight-one								BIT STRING (SIZE (65)),
						four-three								BIT STRING (SIZE (107)),
						six-two									BIT STRING (SIZE (107)),
						twelve-one								BIT STRING (SIZE (129)),
						four-four								BIT STRING (SIZE (139)),
						eight-two								BIT STRING (SIZE (139)),
						sixteen-one								BIT STRING (SIZE (129))
					},
					
					
					typeII-RI-Restriction					BIT STRING (SIZE (2))
				}, 
				typeII-PortSelection					SEQUENCE {
					
					portSelectionSamplingSize				ENUMERATED {n1, n2, n3, n4}					OPTIONAL,		 -- Cond TypeII-PortSelection
					
					
					typeII-PortSelectionRI-Restriction		BIT STRING (SIZE (2))
				}
			},
			
			phaseAlphabetSize						ENUMERATED {n4, n8},
			
			subbandAmplitude						BOOLEAN,
			
			numberOfBeams							ENUMERATED {two, three, four}
		}
	}
}





ConfiguredGrantConfig ::=				SEQUENCE {

	
	frequencyHopping             ENUMERATED {mode1, mode2},
	
	cg-DMRS-Configuration		DMRS-UplinkConfig,

	
	mcs-Table					ENUMERATED {qam64, qam256},
	
	
	mcs-TableTransformPrecoder		ENUMERATED {qam256}																	OPTIONAL,	 -- Need S
	
	
	uci-OnPUSCH							SetupRelease { CG-UCI-OnPUSCH },
	
	
	resourceAllocation					ENUMERATED { resourceAllocationType0, resourceAllocationType1, dynamicSwitch },
	
	
	rbg-Size								ENUMERATED {config2}														OPTIONAL,	 -- Need S
									
	
	powerControlLoopToUse					ENUMERATED {n0, n1},
	
	p0-PUSCH-Alpha							P0-PUSCH-AlphaSetId,
	
	
	transformPrecoder						ENUMERATED {enabled}														OPTIONAL,	 -- Need R
	
	
	nrofHARQ-Processes						INTEGER(1..16),
	
	repK									ENUMERATED {n1, n2, n4, n8},
	
	
	repK-RV									ENUMERATED {s1-0231, s2-0303, s3-0000}										OPTIONAL,	 -- Cond RepK
	
	

	
	
	
	
	
	
	
	periodicity								ENUMERATED {
												sym2, sym7, sym1x14, sym2x14, sym4x14, sym5x14, sym8x14, sym10x14, sym16x14, sym20x14,
												sym32x14, sym40x14, sym64x14, sym80x14, sym128x14, sym160x14, sym256x14, sym320x14, sym512x14,
												sym640x14, sym1024x14, sym1280x14, sym2560x14, sym5120x14,

												sym6, sym1x12, sym2x12, sym4x12, sym5x12, sym8x12, sym10x12, sym16x12, sym20x12, sym32x12,
												sym40x12, sym64x12, sym80x12, sym128x12, sym160x12, sym256x12, sym320x12, sym512x12, sym640x12,
												sym1280x12, sym2560x12
											},

	
	
	
	
	configuredGrantTimer					ENUMERATED {
												sym2, sym7, sym1x14, sym2x14, sym4x14, sym5x14, sym8x14, sym10x14, sym16x14, sym20x14, sym32x14,
												sym40x14, sym64x14, sym80x14, sym128x14, sym160x14, sym256x14, sym512x14, sym640x14,

												sym6, sym1x12, sym2x12, sym4x12, sym5x12, sym8x12, sym10x12, sym16x12, sym20x12, sym32x12,
												sym40x12, sym64x12, sym80x12, sym128x12, sym256x12, sym320x12, sym512x12, sym640x12
											}																			OPTIONAL,	 -- Need R
	
	
	rrc-ConfiguredUplinkGrant		SEQUENCE {
			
			timeDomainOffset						INTEGER  (0..5119),
			
			
			timeDomainAllocation					 INTEGER  (0..15), 
            
			
			frequencyDomainAllocation				BIT STRING (SIZE(18)),
			
			
            antennaPort								INTEGER   (0..31),
            dmrs-SeqInitialization					INTEGER   (0..1)          					  OPTIONAL,   -- Cond NoTransformPrecoder
            precodingAndNumberOfLayers				INTEGER   (0..63),
            srs-ResourceIndicator					INTEGER   (0..15),
			
			mcsAndTBS								INTEGER (0..31),
			
			

			frequencyHoppingOffset					INTEGER (1.. maxNrofPhysicalResourceBlocks-1),
			pathlossReferenceIndex					INTEGER (0..maxNrofPUSCH-PathlossReferenceRSs-1),
			...
	}																								OPTIONAL   -- Cond Type1
}

CG-UCI-OnPUSCH ::= CHOICE {
	dynamic									SEQUENCE (SIZE (1..4)) OF BetaOffsets,
	semiStatic								BetaOffsets
}





ControlResourceSet ::= 					SEQUENCE {
	
	
	
	
	controlResourceSetId					ControlResourceSetId,


	
	
	
	
	
	
	
	frequencyDomainResources				BIT STRING (SIZE (45)),
	
	
	duration								INTEGER (1..maxCoReSetDuration),
	
	
	cce-REG-MappingType							CHOICE { 
		interleaved								SEQUENCE {
			
			
			reg-BundleSize							ENUMERATED {n2, n3, n6},
			
			interleaverSize							ENUMERATED {n2, n3, n6}, 
			
			shiftIndex								INTEGER(0..maxNrofPhysicalResourceBlocks-1)
		}, 
		nonInterleaved 							NULL
	},
	
	
	precoderGranularity						ENUMERATED {sameAsREG-bundle, allContiguousRBs},

	
	
	tci-StatesPDCCH							SEQUENCE(SIZE (1..maxNrofTCI-StatesPDCCH)) OF TCI-StateId				OPTIONAL,	 -- Need R

	
	
	
	tci-PresentInDCI						ENUMERATED {enabled}													OPTIONAL, 	 -- Need S

	
	
	pdcch-DMRS-ScramblingID					BIT STRING (SIZE (16))													OPTIONAL 	 -- Need S
}





ControlResourceSetId ::=				INTEGER (0..maxNrofControlResourceSets-1)




CrossCarrierSchedulingConfig ::=		SEQUENCE {
	schedulingCellInfo						CHOICE {
		own										SEQUENCE {					
			cif-Presence							BOOLEAN
		},
		other									SEQUENCE {					
			schedulingCellId						ServCellIndex,
			cif-InSchedulingCell					INTEGER (1..7)
		}																	 -- Cond SCellOnly
	},
	...
}




CSI-AperiodicTriggerStateList ::=	SEQUENCE (SIZE (1..maxNrOfCSI-AperiodicTriggers)) OF CSI-AperiodicTriggerState 

CSI-AperiodicTriggerState ::=		SEQUENCE {
	associatedReportConfigInfoList		SEQUENCE (SIZE(1..maxNrofReportConfigPerAperiodicTrigger)) OF CSI-AssociatedReportConfigInfo,
	...	
}

CSI-AssociatedReportConfigInfo ::=		SEQUENCE {
	
	reportConfigId						CSI-ReportConfigId,

	resourcesForChannel					CHOICE {
       nzp-CSI-RS							SEQUENCE {
			
			
			
			resourceSet		INTEGER (1..maxNrofNZP-CSI-RS-ResourceSetsPerConfig),

			
			
			
			
			
			qcl-info						SEQUENCE (SIZE(1..maxNrofAP-CSI-RS-ResourcesPerSet)) OF TCI-StateId
		},
		
		
		
		csi-SSB-ResourceSet					INTEGER (1..maxNrofCSI-SSB-ResourceSetsPerConfig)
	},

	
	
	
	
	
	
	csi-IM-ResourcesforInteference				INTEGER(1..maxNrofCSI-IM-ResourceSetsPerConfig)			OPTIONAL,  --Cond CSI-IM-forInterference


	
	
	
	
	
	
	nzp-CSI-RS-ResourcesforInterference			INTEGER (1..maxNrofNZP-CSI-RS-ResourceSetsPerConfig)	OPTIONAL,  --Cond LinkedNZP-CSI-RS-forInterference
	...
}





CSI-FrequencyOccupation ::=				SEQUENCE {
	
	
	startingRB								INTEGER (0..maxNrofPhysicalResourceBlocks-1),
	
	
	nrofRBs									INTEGER (24..maxNrofPhysicalResourceBlocks),
	...
}




CSI-IM-Resource ::= 			SEQUENCE {
	csi-IM-ResourceId						CSI-IM-ResourceId,

	
	
	csi-IM-ResourceElementPattern				CHOICE {
		pattern0									SEQUENCE {
			
			
			subcarrierLocation-p0						ENUMERATED { s0, s2, s4, s6, s8, s10 },
			
			
			symbolLocation-p0							INTEGER (0..12)
		},
		pattern1									SEQUENCE {
			
			
			subcarrierLocation-p1						ENUMERATED { s0, s4, s8 },
			
			
			symbolLocation-p1							INTEGER (0..13)
		}
	}																										OPTIONAL,	 --Need M

	
	freqBand									CSI-FrequencyOccupation										OPTIONAL,	 -- Need M

	
	periodicityAndOffset					CSI-ResourcePeriodicityAndOffset								OPTIONAL,  --Cond PeriodicOrSemiPersistent
	...
}




CSI-IM-ResourceId ::= 			INTEGER (0..maxNrofCSI-IM-Resources-1) 




CSI-IM-ResourceSet ::=			SEQUENCE {

	csi-IM-ResourceSetId					CSI-IM-ResourceSetId,
	
	
	csi-IM-Resources						SEQUENCE (SIZE(1..maxNrofCSI-IM-ResourcesPerSet)) OF CSI-IM-ResourceId,
	...
}




CSI-IM-ResourceSetId ::=				INTEGER (0..maxNrofCSI-IM-ResourceSets-1)





CSI-MeasConfig ::=					SEQUENCE {
	
    nzp-CSI-RS-ResourceToAddModList		SEQUENCE (SIZE (1..maxNrofNZP-CSI-RS-Resources)) OF NZP-CSI-RS-Resource					OPTIONAL,  -- Need N
	nzp-CSI-RS-ResourceToReleaseList	SEQUENCE (SIZE (1..maxNrofNZP-CSI-RS-Resources)) OF NZP-CSI-RS-ResourceId				OPTIONAL,  -- Need N

	
	nzp-CSI-RS-ResourceSetToAddModList	SEQUENCE (SIZE (1..maxNrofNZP-CSI-RS-ResourceSets)) OF NZP-CSI-RS-ResourceSet			OPTIONAL,  -- Need N
	nzp-CSI-RS-ResourceSetToReleaseList	SEQUENCE (SIZE (1..maxNrofNZP-CSI-RS-ResourceSets)) OF NZP-CSI-RS-ResourceSetId			OPTIONAL,  -- Need N

	
	csi-IM-ResourceToAddModList			SEQUENCE (SIZE (1..maxNrofCSI-IM-Resources)) OF CSI-IM-Resource							OPTIONAL,  -- Need N
	csi-IM-ResourceToReleaseList		SEQUENCE (SIZE (1..maxNrofCSI-IM-Resources)) OF CSI-IM-ResourceId						OPTIONAL,  -- Need N

	
	csi-IM-ResourceSetToAddModList		SEQUENCE (SIZE (1..maxNrofCSI-IM-ResourceSets)) OF CSI-IM-ResourceSet					OPTIONAL,  -- Need N
	csi-IM-ResourceSetToReleaseList		SEQUENCE (SIZE (1..maxNrofCSI-IM-ResourceSets)) OF CSI-IM-ResourceSetId					OPTIONAL,  -- Need N

	
	csi-SSB-ResourceSetToAddModList		SEQUENCE (SIZE (1..maxNrofCSI-SSB-ResourceSets)) OF CSI-SSB-ResourceSet					OPTIONAL,  -- Need N
	csi-SSB-ResourceSetToAddReleaseList	SEQUENCE (SIZE (1..maxNrofCSI-SSB-ResourceSets)) OF CSI-SSB-ResourceSetId				OPTIONAL,  -- Need N

	
	csi-ResourceConfigToAddModList 		SEQUENCE (SIZE (1..maxNrofCSI-ResourceConfigurations)) OF CSI-ResourceConfig			OPTIONAL,  -- Need N
	csi-ResourceConfigToReleaseList 	SEQUENCE (SIZE (1..maxNrofCSI-ResourceConfigurations)) OF CSI-ResourceConfigId			OPTIONAL,  -- Need N

	
	csi-ReportConfigToAddModList		SEQUENCE (SIZE (1..maxNrofCSI-ReportConfigurations)) OF CSI-ReportConfig				OPTIONAL,  -- Need N
	csi-ReportConfigToReleaseList		SEQUENCE (SIZE (1..maxNrofCSI-ReportConfigurations)) OF CSI-ReportConfigId				OPTIONAL,  -- Need N
	

	
	reportTriggerSize				INTEGER (0..6)																				OPTIONAL,

	
	
	
	aperiodicTriggerStateList			SetupRelease { CSI-AperiodicTriggerStateList }											OPTIONAL,  -- Need M
	semiPersistentOnPUSCH-TriggerStateList			SetupRelease { CSI-SemiPersistentOnPUSCH-TriggerStateList }					OPTIONAL,  -- Need M
	...
}

maxNrofNZP-CSI-RS-ResourceSets		INTEGER ::= 		64
maxNrofNZP-CSI-RS-ResourceSets-1	INTEGER ::= 		63

maxNrofCSI-SSB-ResourceSets 		INTEGER ::=			64
maxNrofCSI-SSB-ResourceSets-1 		INTEGER ::=			63

maxNrofCSI-IM-ResourceSets 			INTEGER ::=			64
maxNrofCSI-IM-ResourceSets-1		INTEGER ::=			63





CSI-ReportConfig ::=			SEQUENCE {
	reportConfigId							CSI-ReportConfigId,

	
	
	carrier									ServCellIndex			OPTIONAL,	 -- Need S

	
	
	resourcesForChannelMeasurement			CSI-ResourceConfigId,

	
	
	
	csi-IM-ResourcesForInterference			CSI-ResourceConfigId	OPTIONAL,	 -- Need R

	
	
	
	nzp-CSI-RS-ResourcesForInterference		CSI-ResourceConfigId	OPTIONAL, 	 -- Need R

	
	reportConfigType						CHOICE {
		periodic								SEQUENCE {
			
			
			reportSlotConfig						CSI-ReportPeriodicityAndOffset,
			
			pucch-CSI-ResourceList					SEQUENCE (SIZE (1..maxNrofBWPs)) OF PUCCH-CSI-Resource
		},
		semiPersistentOnPUCCH					SEQUENCE {
			
			
			reportSlotConfig						CSI-ReportPeriodicityAndOffset,
			
			pucch-CSI-ResourceList					SEQUENCE (SIZE (1..maxNrofBWPs)) OF PUCCH-CSI-Resource
		},
		semiPersistentOnPUSCH					SEQUENCE {
			
			reportSlotConfig						ENUMERATED {sl5, sl10, sl20, sl40, sl80, sl160, sl320},
			
			
			
			reportSlotOffsetList				SEQUENCE (SIZE (1..4)) OF INTEGER (0..7),
			
			
			
			csi-RNTI								RNTI-Value,
			
			
			p0alpha									P0-PUSCH-AlphaSetId
		},
		aperiodic								SEQUENCE {
			
			
			
			
			reportSlotOffsetList				SEQUENCE (SIZE (1..16)) OF INTEGER (0..7)
		}
	},
	
	reportQuantity							CHOICE {
		none									NULL,
		cri-RI-PMI-CQI							NULL, 
		cri-RI-i1								NULL, 
		cri-RI-i1-CQI							SEQUENCE {
			
			
			pdsch-BundleSizeForCSI					ENUMERATED {n2, n4}		OPTIONAL
		}, 
		cri-RI-CQI								NULL, 
		cri-RSRP								NULL, 
		ssb-Index-RSRP							NULL,
		cri-RI-LI-PMI-CQI						NULL
	},
	
	reportFreqConfiguration					 SEQUENCE {
		
		cqi-FormatIndicator						ENUMERATED { widebandCQI, subbandCQI },
		
		pmi-FormatIndicator						ENUMERATED { widebandPMI, subbandPMI },
		
		
		
		
		
		csi-ReportingBand						CHOICE {
			subbands3								BIT STRING(SIZE(3)),
			subbands4								BIT STRING(SIZE(4)),
			subbands5								BIT STRING(SIZE(5)),
			subbands6								BIT STRING(SIZE(6)),
			subbands7								BIT STRING(SIZE(7)),
			subbands8								BIT STRING(SIZE(8)),
			subbands9								BIT STRING(SIZE(9)),
			subbands10								BIT STRING(SIZE(10)),
			subbands11								BIT STRING(SIZE(11)),
			subbands12								BIT STRING(SIZE(12)),
			subbands13								BIT STRING(SIZE(13)),
			subbands14								BIT STRING(SIZE(14)),
			subbands15								BIT STRING(SIZE(15)),
			subbands16								BIT STRING(SIZE(16)),
			subbands17								BIT STRING(SIZE(17)),
			subbands18								BIT STRING(SIZE(18)),
			...
		}	OPTIONAL	 -- Need S

	},
	
	
	timeRestrictionForChannelMeasurements				ENUMERATED {configured, notConfigured},
	
	
	timeRestrictionForInterferenceMeasurements			ENUMERATED {configured, notConfigured},
	
	codebookConfig								CodebookConfig,
	
	nrofCQIsPerReport							ENUMERATED {n1, n2},
	
	groupBasedBeamReporting						CHOICE {
		enabled										NULL,
		disabled 									SEQUENCE {
			
			
			
			
			
			
			
			nrofReportedRS							ENUMERATED {n1, n2, n3, n4}												OPTIONAL	 -- Need S
		}
	},

	
	cqi-Table								ENUMERATED {table1, table2, spare2, spare1}										OPTIONAL,
	
	
	subbandSize								ENUMERATED {value1, value2},
	
	
	
	bler-Target								ENUMERATED {zerodot1, spare3, space2, spare1}										OPTIONAL,
	
	
	
	
	
	
	
	
	
	
	
	
	
	non-PMI-PortIndication					SEQUENCE (SIZE (1..maxNrofNZP-CSI-RS-ResourcesPerConfig)) OF PortIndexFor8Ranks		OPTIONAL,	...
}

CSI-ReportPeriodicityAndOffset ::= CHOICE {
	slots4								INTEGER(0..3),
	slots5								INTEGER(0..4),
	slots8								INTEGER(0..7),
	slots10								INTEGER(0..9),
	slots16								INTEGER(0..15),
	slots20								INTEGER(0..19),
	slots40								INTEGER(0..39),
	slots80								INTEGER(0..79),
	slots160							INTEGER(0..159),
	slots320							INTEGER(0..319)
}

PUCCH-CSI-Resource ::= 				CHOICE {
	uplinkBandwidthPartId				BWP-Id,
	
	pucch-Resource						PUCCH-Resource
}




PortIndexFor8Ranks ::=	CHOICE {
	portIndex8				SEQUENCE{
		rank1-8					PortIndex8,
		rank2-8					SEQUENCE(SIZE(1..2)) OF PortIndex8,
		rank3-8					SEQUENCE(SIZE(1..3)) OF PortIndex8,
		rank4-8					SEQUENCE(SIZE(1..4)) OF PortIndex8,
		rank5-8					SEQUENCE(SIZE(1..5)) OF PortIndex8,
		rank6-8					SEQUENCE(SIZE(1..6)) OF PortIndex8,
		rank7-8					SEQUENCE(SIZE(1..7)) OF PortIndex8,
		rank8-8					SEQUENCE(SIZE(1..8)) OF PortIndex8
	},
	portIndex4				SEQUENCE{
		rank1-4					PortIndex4,
		rank2-4					SEQUENCE(SIZE(1..2)) OF PortIndex4,
		rank3-4					SEQUENCE(SIZE(1..3)) OF PortIndex4,
		rank4-4					SEQUENCE(SIZE(1..4)) OF PortIndex4
	},
	portIndex2				SEQUENCE{
		rank1-2					PortIndex2,
		rank2-2					SEQUENCE(SIZE(1..2)) OF PortIndex2
	},
	portIndex1				NULL
}

PortIndex8::=	INTEGER (0..7)
PortIndex4::=	INTEGER (0..3)
PortIndex2::=	INTEGER (0..1)

maxNrofNZP-CSI-RS-ResourcesPerConfig	INTEGER ::=	128



CSI-ReportConfigId ::= 					INTEGER (0..maxNrofCSI-ReportConfigurations-1)






CSI-ResourceConfig ::= 		SEQUENCE {

	
	csi-ResourceConfigId				CSI-ResourceConfigId,

	
	
	csi-RS-ResourceSetList 	 			CHOICE {
		nzp-CSI-RS-SSB 						SEQUENCE {
			nzp-CSI-RS-ResourceSetList			SEQUENCE (SIZE (1..maxNrofNZP-CSI-RS-ResourceSetsPerConfig)) OF NZP-CSI-RS-ResourceSetId OPTIONAL,
			
			
			csi-SSB-ResourceSetList				SEQUENCE (SIZE (1..maxNrofCSI-SSB-ResourceSetsPerConfig)) OF CSI-SSB-ResourceSetId	OPTIONAL
		},			
		csi-IM-ResourceSetList				SEQUENCE (SIZE (1..maxNrofCSI-IM-ResourceSetsPerConfig)) OF CSI-IM-ResourceSetId
	},


	
	
	bwp-Id								BWP-Id,

	
	resourceType						ENUMERATED { aperiodic, semiPersistent, periodic },
	...
}




CSI-ResourceConfigId ::= INTEGER (0..maxNrofCSI-ResourceConfigurations-1)





CSI-ResourcePeriodicityAndOffset ::=	CHOICE {
	slots4							INTEGER (0..3), 
	slots5							INTEGER (0..4), 
	slots8							INTEGER (0..7), 
	slots10							INTEGER (0..9), 
	slots16							INTEGER (0..15), 
	slots20							INTEGER (0..19), 
	slots32							INTEGER (0..31), 
	slots40							INTEGER (0..39), 
	slots64							INTEGER (0..63), 
	slots80							INTEGER (0..79), 
	slots160						INTEGER (0..159), 
	slots320						INTEGER (0..319), 
	slots640						INTEGER (0..639)
}





CSI-RS-ResourceMapping ::= 				SEQUENCE {
	
	
	
	frequencyDomainAllocation			CHOICE {
		row1								BIT STRING (SIZE (4)),
		row2								BIT STRING (SIZE (12)),
		row4								BIT STRING (SIZE (3)),
		other								BIT STRING (SIZE (6))
	},
	
	nrofPorts							ENUMERATED {p1,p2,p4,p8,p12,p16,p24,p32},
	
	
	firstOFDMSymbolInTimeDomain			INTEGER (0..13),
	
	firstOFDMSymbolInTimeDomain2		INTEGER (0..13)																OPTIONAL,	 -- Need R
	
	cdm-Type								ENUMERATED {noCDM, fd-CDM2, cdm4-FD2-TD2, cdm8-FD2-TD4},
	
	
	
	
	
	density									CHOICE {
		dot5									ENUMERATED {evenPRBs, oddPRBs}, 
		one										NULL, 
		three									NULL, 
		spare									NULL
	},
	
	freqBand								CSI-FrequencyOccupation,
	...
}





CSI-SemiPersistentOnPUSCH-TriggerStateList ::=	SEQUENCE(SIZE (1..maxNrOfSemiPersistentPUSCH-Triggers)) OF CSI-SemiPersistentOnPUSCH-TriggerState
CSI-SemiPersistentOnPUSCH-TriggerState ::=		SEQUENCE {
	associatedReportConfigInfo						CSI-ReportConfigId,
	...
}

maxNrOfSemiPersistentPUSCH-Triggers					INTEGER ::= 64		





CSI-SSB-ResourceSetId ::=	INTEGER (0..maxNrofCSI-SSB-ResourceSets-1)





CSI-SSB-ResourceSet ::=						SEQUENCE {
	csi-SSB-ResourceSetId						CSI-SSB-ResourceSetId,
	csi-SSB-ResourceList						SEQUENCE (SIZE(1..maxNrofCSI-SSB-ResourcePerSet)) OF SSB-Index,
	...
}





DMRS-DownlinkConfig ::=					SEQUENCE {
	
	
	dmrs-Type								ENUMERATED {type2}													OPTIONAL,	 -- Need R
	
	
	
	dmrs-AdditionalPosition					ENUMERATED {pos0, pos1, pos3}										OPTIONAL,	 -- Need R
	
	dmrs-group1								BIT STRING (SIZE (12))												OPTIONAL,	 -- Need R
	
	dmrs-group2								BIT STRING (SIZE (12))												OPTIONAL,	 -- Need R
	
	
	
	maxLength								ENUMERATED {len2}													OPTIONAL, 	 -- Need R
	
	
	
	scramblingID0							INTEGER (0..65535)													OPTIONAL, 	 -- Need S
	
	
	scramblingID1							INTEGER (0..65535)													OPTIONAL, 	 -- Need S

	
	phaseTrackingRS						SetupRelease { PTRS-DownlinkConfig	}									OPTIONAL,	 -- Need M

	...
}





DMRS-UplinkConfig ::=					SEQUENCE {
	
	
	dmrs-Type								ENUMERATED {type2} 													OPTIONAL,	 -- Need R
	
	
	
	dmrs-AdditionalPosition					ENUMERATED {pos0, pos1, pos3}										OPTIONAL,	 -- Need R
	
	phaseTrackingRS						SetupRelease { PTRS-UplinkConfig }										OPTIONAL,	 -- Need M
	
	
	
	maxLength								ENUMERATED {len2}													OPTIONAL, 	 -- Need R

	transformPrecoding					CHOICE {
		
		disabled									SEQUENCE {
			
			
			
			scramblingID0							INTEGER (0..65535)											OPTIONAL,	 -- Need S
			
			
			
			scramblingID1							INTEGER (0..65535)											OPTIONAL		 -- Need S

		},
		
		enabled								SEQUENCE {
			
			
			nPUSCH-Identity							INTEGER(0..1007)											OPTIONAL,	 -- Need S
			
			
			
			disableSequenceGroupHopping				ENUMERATED {disabled}										OPTIONAL,	 -- Need S
			
			
			
			sequenceHoppingEnabled					ENUMERATED {enabled}										OPTIONAL	 -- Need S
		}
	},
	...
}






DownlinkPreemption ::=						SEQUENCE {
	
	
	int-RNTI								RNTI-Value,

	
	
	timeFrequencySet						ENUMERATED {set0, set1},

	
	
	dci-PayloadSize							INTEGER (0..maxINT-DCI-PayloadSize),

	
	
	int-ConfigurationPerServingCell			SEQUENCE (SIZE (1..maxNrofServingCells)) OF INT-ConfigurationPerServingCell,
	...
}

INT-ConfigurationPerServingCell ::= 		SEQUENCE {
	servingCellId							ServCellIndex,
	
	
	positionInDCI							INTEGER (0..maxINT-DCI-PayloadSize-1)
}





DRB-Identity ::=					INTEGER (1..32)





EUTRA-MBSFN-SubframeConfigList ::= 		SEQUENCE (SIZE (1..maxMBSFN-Allocations)) OF EUTRA-MBSFN-SubframeConfig

EUTRA-MBSFN-SubframeConfig ::=			SEQUENCE {
	
	radioframeAllocationPeriod			ENUMERATED {n1, n2, n4, n8, n16, n32},
	
	radioframeAllocationOffset			INTEGER (0..7),
	
	subframeAllocation					CHOICE {
		
		oneFrame							BIT STRING (SIZE(6)),
		
		fourFrames							BIT STRING (SIZE(24))
	},
	subframeAllocation-v1430			CHOICE {
		
		oneFrame-v1430						BIT STRING (SIZE(2)),
		
		fourFrames-v1430					BIT STRING (SIZE(8))
	}																														OPTIONAL,	 -- Need R
	...
}




FilterCoefficient ::=					ENUMERATED {
											fc0, fc1, fc2, fc3, fc4, fc5,
											fc6, fc7, fc8, fc9, fc11, fc13, 
											fc15, fc17, fc19, spare1, ...}




FreqBandIndicatorNR ::=     		INTEGER (1..1024)





FrequencyInfoDL ::= 				SEQUENCE {
	
	
	
	absoluteFrequencySSB					ARFCN-ValueNR,
	
	
	
	ssb-SubcarrierOffset					INTEGER (1..23)																OPTIONAL,	 -- Need S
	
	
	frequencyBandList					MultiFrequencyBandListNR,
	
	
	
	absoluteFrequencyPointA					ARFCN-ValueNR,

	
	
	scs-SpecificCarrierList					SEQUENCE (SIZE (1..maxSCSs)) OF SCS-SpecificCarrier,
	...
}





FrequencyInfoUL ::= 				SEQUENCE {
	
	
	frequencyBandList					MultiFrequencyBandListNR										OPTIONAL,	 -- Cond FDD-OrSUL
	
	
	absoluteFrequencyPointA						ARFCN-ValueNR					OPTIONAL,	 -- Cond FDD-OrSUL
	
	
	
	scs-SpecificCarriers				SEQUENCE (SIZE (1..maxSCSs)) OF SCS-SpecificCarrier,

	
	
	additionalSpectrumEmission			AdditionalSpectrumEmission										OPTIONAL,	 -- Need S
	
	
	p-Max								P-Max															OPTIONAL,	 -- Need S
	
	frequencyShift7p5khz				ENUMERATED {true}												OPTIONAL,	 -- Cond FDD-OrSUL-Optional
	...
}





GSCN-ValueNR ::=				INTEGER (1..28557)





Hysteresis ::=							INTEGER (0..30)




LogicalChannelConfig ::=		SEQUENCE {
	ul-SpecificParameters			SEQUENCE {
		priority						INTEGER (1..16),
		prioritisedBitRate				ENUMERATED {kBps0, kBps8, kBps16, kBps32, kBps64, kBps128, kBps256, kBps512, 
											kBps1024, kBps2048, kBps4096, kBps8192, kBps16384, kBps32768, kBps65536, infinity},
		bucketSizeDuration				ENUMERATED {ms50, ms100, ms150, ms300, ms500, ms1000, spare2, spare1},

		allowedServingCells				SEQUENCE (SIZE (1..maxNrofServingCells-1)) OF ServCellIndex					OPTIONAL,	 -- Need R
		allowedSCS-List					SEQUENCE (SIZE (1..maxSCSs)) OF SubcarrierSpacing							OPTIONAL,	 -- Need R
		maxPUSCH-Duration				ENUMERATED { ms0p02, ms0p04, ms0p0625, ms0p125, ms0p25, ms0p5, spare2, spare1 }												OPTIONAL,	 -- Need R
		configuredGrantType1Allowed		ENUMERATED {true}															OPTIONAL,	 -- Need R

		logicalChannelGroup				INTEGER (0..maxLCG-ID)														OPTIONAL, 	 -- Need R
		schedulingRequestID				SchedulingRequestId															OPTIONAL,	 -- Need R
		logicalChannelSR-Mask			BOOLEAN,
		logicalChannelSR-DelayTimerApplied	BOOLEAN
	}																												OPTIONAL,		 -- Cond UL

	
	...
}





MAC-CellGroupConfig ::= 			SEQUENCE {
	drx-Config							SetupRelease { DRX-Config }																OPTIONAL,  -- Need M

	schedulingRequestConfig				SchedulingRequestConfig																OPTIONAL,  -- Need M
	bsr-Config							BSR-Config																	OPTIONAL,	 -- Need M
	tag-Config							TAG-Config																	OPTIONAL,	 -- Need M	
	phr-Config							SetupRelease { PHR-Config }																OPTIONAL,	 -- Need M
	
	skipUplinkTxDynamic					BOOLEAN,
	
	cs-RNTI								SetupRelease { RNTI-Value }															OPTIONAL	 -- Need M
}

DRX-Config ::=						SEQUENCE {
	drx-onDurationTimer					CHOICE {
											subMilliSeconds	INTEGER (1..31),
											milliSeconds	ENUMERATED {
											ms1, ms2, ms3, ms4, ms5, ms6, ms8, ms10, ms20, ms30, ms40, ms50, ms60, 
											ms80, ms100, ms200, ms300, ms400, ms500, ms600, ms800, ms1000, ms1200, 
											ms1600, spare9, spare8, spare7, spare6, spare5, spare4, spare3, spare2, spare1 }
											},
	drx-InactivityTimer					ENUMERATED { 
											ms0, ms1, ms2, ms3, ms4, ms5, ms6, ms8, ms10, ms20, ms30, ms40, ms50, ms60, ms80, 
											ms100, ms200, ms300, ms500, ms750, ms1280, ms1920, ms2560, spare9, spare8, 
											spare7, spare6, spare5, spare4, spare3, spare2, spare1},
	drx-HARQ-RTT-TimerDL				INTEGER (0..56),
	drx-HARQ-RTT-TimerUL				INTEGER (0..56),
	drx-RetransmissionTimerDL			ENUMERATED { 
											sl0, sl1, sl2, sl4, sl6, sl8, sl16, sl24, sl33, sl40, sl64, sl80, sl96, sl112, sl128, 
											sl160, sl320, spare15, spare14, spare13, spare12, spare11, spare10, spare9, 
											spare8, spare7, spare6, spare5, spare4, spare3, spare2, spare1},
	drx-RetransmissionTimerUL			ENUMERATED {
											sl0, sl1, sl2, sl4, sl6, sl8, sl16, sl24, sl33, sl40, sl64, sl80, sl96, sl112, sl128, 
											sl160, sl320, spare15, spare14, spare13, spare12, spare11, spare10, spare9, 
											spare8, spare7, spare6, spare5, spare4, spare3, spare2, spare1 },
	drx-LongCycleStartOffset		CHOICE {
		ms10							INTEGER(0..9),
		ms20							INTEGER(0..19),
		ms32							INTEGER(0..31),
		ms40							INTEGER(0..39),
		ms60							INTEGER(0..59),
		ms64							INTEGER(0..63),
		ms70							INTEGER(0..69),
		ms80							INTEGER(0..79),
		ms128							INTEGER(0..127),
		ms160							INTEGER(0..159),
		ms256							INTEGER(0..255),
		ms320							INTEGER(0..319),
		ms512							INTEGER(0..511),
		ms640							INTEGER(0..639),
		ms1024							INTEGER(0..1023),
		ms1280							INTEGER(0..1279),
		ms2048							INTEGER(0..2047),
		ms2560							INTEGER(0..2559),
		ms5120							INTEGER(0..5119),
		ms10240							INTEGER(0..10239)
	},
	
	
	shortDRX							SEQUENCE {
		drx-ShortCycle						ENUMERATED	{
												ms2, ms3, ms4, ms5, ms6, ms7, ms8, ms10, ms14, ms16, ms20, ms30, ms32,
												ms35, ms40, ms64, ms80, ms128, ms160, ms256, ms320, ms512, ms640, spare9,
												spare8, spare7, spare6, spare5, spare4, spare3, spare2, spare1 },
		drx-ShortCycleTimer					INTEGER (1..16)
	}		OPTIONAL,													 -- Need R
	drx-SlotOffset						INTEGER (0..31)

}

PHR-Config ::=						SEQUENCE {
	phr-PeriodicTimer					ENUMERATED {sf10, sf20, sf50, sf100, sf200,sf500, sf1000, infinity},
	phr-ProhibitTimer					ENUMERATED {sf0, sf10, sf20, sf50, sf100,sf200, sf500, sf1000},
	phr-Tx-PowerFactorChange			ENUMERATED {dB1, dB3, dB6, infinity},
	multiplePHR							BOOLEAN,
	phr-Type2PCell						BOOLEAN,
	phr-Type2OtherCell					BOOLEAN,
	phr-ModeOtherCG						ENUMERATED {real, virtual}

}


TAG-Config ::=				SEQUENCE {
	tag-ToReleaseList			SEQUENCE (SIZE (1..maxNrofTAGs)) OF TAG-Id											OPTIONAL,	 -- Need N
	tag-ToAddModList			SEQUENCE (SIZE (1..maxNrofTAGs)) OF TAG-ToAddMod											OPTIONAL		 -- Need N
}

TAG-ToAddMod ::= 			SEQUENCE {
	tag-Id						TAG-Id,
	timeAlignmentTimer			TimeAlignmentTimer,
	...
}

TAG-Id ::=					INTEGER (0..maxNrofTAGs-1)

TimeAlignmentTimer ::= 		ENUMERATED {ms500, ms750, ms1280, ms1920, ms2560, ms5120, ms10240, infinity}

BSR-Config ::=				SEQUENCE {
	periodicBSR-Timer			ENUMERATED {
									sf1, sf5, sf10, sf16, sf20, sf32, sf40, sf64, sf80, sf128, sf160, sf320, sf640, sf1280, sf2560, infinity},
	retxBSR-Timer				ENUMERATED { sf10, sf20, sf40, sf80, sf160, sf320, sf640, sf1280, sf2560, sf5120, sf10240, spare5, spare4,
											spare3, spare2, spare1},
	logicalChannelSR-DelayTimer		ENUMERATED { sf20, sf40, sf64, sf128, sf512, sf1024, sf2560, spare1}	OPTIONAL	 -- Need R
}







MeasConfig ::=							SEQUENCE {
	
	measObjectToRemoveList					MeasObjectToRemoveList											OPTIONAL,	 -- Need N
	measObjectToAddModList					MeasObjectToAddModList											OPTIONAL,	 -- Need N

	
	reportConfigToRemoveList				ReportConfigToRemoveList										OPTIONAL,	 -- Need N
	reportConfigToAddModList				ReportConfigToAddModList										OPTIONAL,	 -- Need N

	
	measIdToRemoveList						MeasIdToRemoveList												OPTIONAL,	 -- Need N
	measIdToAddModList						MeasIdToAddModList												OPTIONAL,	 -- Need N

	
	
	s-MeasureConfig							CHOICE {
		ssb-RSRP								RSRP-Range,						
		csi-RSRP								RSRP-Range						
	} 																										OPTIONAL,	 -- Need M

	quantityConfig						QuantityConfig														OPTIONAL,	 -- Need M

	
	measGapConfig							MeasGapConfig													OPTIONAL,	 -- Need M
	...
}

MeasObjectToRemoveList ::=				SEQUENCE (SIZE (1..maxNrofObjectId)) OF MeasObjectId

MeasIdToRemoveList ::=					SEQUENCE (SIZE (1..maxNrofMeasId)) OF MeasId

ReportConfigToRemoveList ::=			SEQUENCE (SIZE (1..maxReportConfigId)) OF ReportConfigId





MeasGapConfig ::=				SEQUENCE {
		gapFR2 						SetupRelease { GapConfig }				OPTIONAL,
		...
}

GapConfig ::=					SEQUENCE {
		gapOffset 					INTEGER (0..159),
		mgl 						ENUMERATED {ms1dot5, ms3, ms3dot5, ms4, ms5dot5, ms6},
		mgrp 						ENUMERATED {ms20, ms40, ms80, ms160},
		mgta						ENUMERATED {ms0, ms0dot25, ms0dot5},
		...
}





MeasId ::=							INTEGER (1..maxNrofMeasId)





MeasIdToAddModList ::=				SEQUENCE (SIZE (1..maxNrofMeasId)) OF MeasIdToAddMod

MeasIdToAddMod ::=					SEQUENCE {
	measId								MeasId,
	measObjectId						MeasObjectId,
	reportConfigId						ReportConfigId
}





MeasObjectId ::=							INTEGER (1..maxNrofObjectId)





MeasObjectNR ::=							SEQUENCE {
	ssbFrequency								ARFCN-ValueNR															OPTIONAL,
	refFreqCSI-RS								ARFCN-ValueNR															OPTIONAL,

	
	referenceSignalConfig						ReferenceSignalConfig,													

	
	absThreshSS-BlocksConsolidation			ThresholdNR																	OPTIONAL,	 -- Need R
	absThreshCSI-RS-Consolidation			ThresholdNR																	OPTIONAL,	 -- Need R
																													
	
	nrofSS-BlocksToAverage					INTEGER (2..maxNrofSS-BlocksToAverage)										OPTIONAL,	 -- Need R
	nrofCSI-RS-ResourcesToAverage			INTEGER (2..maxNrofCSI-RS-ResourcesToAverage)								OPTIONAL,	 -- Need R
																															
	
	quantityConfigIndex							INTEGER (1..maxNrofQuantityConfig),

	
	offsetFreq									Q-OffsetRangeList,

	
	cellsToRemoveList							PCI-List																OPTIONAL,	 -- Need N
	cellsToAddModList							CellsToAddModList														OPTIONAL,	 -- Need N

	
	blackCellsToRemoveList						PCI-RangeIndexList														OPTIONAL,	 -- Need N
	blackCellsToAddModList						BlackCellsToAddModList													OPTIONAL,	 -- Need N

	
	whiteCellsToRemoveList						PCI-RangeIndexList														OPTIONAL,	 -- Need N
	whiteCellsToAddModList						WhiteCellsToAddModList													OPTIONAL,	 -- Need N
	...
}

ReferenceSignalConfig::=     			SEQUENCE {
	

	
	ssb-ConfigMobility						SSB-ConfigMobility				OPTIONAL,	 -- Need M
	
	csi-rs-ResourceConfigMobility			SetupRelease { CSI-RS-ResourceConfigMobility } OPTIONAL -- Need M		

}


SSB-ConfigMobility::= 	SEQUENCE {
		
		subcarrierSpacing                    SubcarrierSpacing,
		
		
		
		
		ssb-ToMeasure							SetupRelease { SSB-ToMeasure }								OPTIONAL,	 -- Need M

	
	useServingCellTimingForSync				BOOLEAN,
																									
	
	smtc1									SEQUENCE {
		
		
		
		
		periodicityAndOffset					CHOICE {
			sf5										INTEGER (0..4),
			sf10									INTEGER (0..9),
			sf20									INTEGER (0..19),
			sf40									INTEGER (0..39),
			sf80									INTEGER (0..79),
			sf160									INTEGER (0..159)
		},
		
		
		duration								ENUMERATED { sf1, sf2, sf3, sf4, sf5 }
	},

	
	
	smtc2 									SEQUENCE {
		
		pci-List								SEQUENCE (SIZE (1..maxNrofPCIsPerSMTC)) OF PhysCellId		OPTIONAL,	 -- Need M
		
		periodicity								ENUMERATED {sf5, sf10, sf20, sf40, sf80, sf160, spare2, spare1}
	}																										OPTIONAL, -- Cond IntraFreqConnected
	ss-RSSI-Measurement							SEQUENCE {
		measurementSlots							CHOICE {
			kHz15										BIT STRING (SIZE(1)),
			kHz30										BIT STRING (SIZE(2)),
			kHz60										BIT STRING (SIZE(4)),
			kHz120										BIT STRING (SIZE(8))
		},
		endSymbol									INTEGER(0..13)
	}																										OPTIONAL				
}

CSI-RS-ResourceConfigMobility ::= 		SEQUENCE {
	
		isServingCellMO						BOOLEAN,
	
	
	
	subcarrierSpacing						SubcarrierSpacing,
	
	csi-RS-CellList-Mobility 	SEQUENCE (SIZE (1..maxNrofCSI-RS-CellsRRM))	OF CSI-RS-CellMobility

}

CSI-RS-CellMobility ::=				SEQUENCE {
	cellId									PhysCellId,

	csi-rs-MeasurementBW					SEQUENCE {
		
		
		nrofPRBs			ENUMERATED { size24, size48, size96, size192, size264},
		
		
		
		startPRB			INTEGER(0..2169)
	},

	
	
	density									ENUMERATED {d1,d3}												OPTIONAL,



	csi-rs-ResourceList-Mobility 	SEQUENCE (SIZE (1..maxNrofCSI-RS-ResourcesRRM))	OF CSI-RS-Resource-Mobility
}


CSI-RS-Resource-Mobility ::=			SEQUENCE {
	csi-RS-Index							CSI-RS-Index,
	
	slotConfig								CHOICE {
		ms4										INTEGER (0..31),
		ms5										INTEGER (0..39),
		ms10									INTEGER (0..79),
		ms20									INTEGER (0..159),
		ms40									INTEGER (0..319)
	},
	
	
	
	
	associatedSSB							SEQUENCE {
		ssb-Index								SSB-Index,
		
		
		isQuasiColocated						BOOLEAN
	}					OPTIONAL,  -- Cond AssociatedSSB

	
	
	
	
	frequencyDomainAllocation			CHOICE {
		row1								BIT STRING (SIZE (4)),
		row2								BIT STRING (SIZE (12))
	},

	
	
	
	firstOFDMSymbolInTimeDomain			INTEGER (0..13),	
	
	sequenceGenerationConfig				INTEGER (0..1023),
	...
}

CSI-RS-Index ::= 				INTEGER (0..maxNrofCSI-RS-ResourcesRRM-1)

Q-OffsetRangeList ::=					SEQUENCE {
	rsrpOffsetSSB							Q-OffsetRange				DEFAULT dB0,
	rsrqOffsetSSB							Q-OffsetRange				DEFAULT dB0,
	sinrOffsetSSB							Q-OffsetRange				DEFAULT dB0,
	rsrpOffsetCSI-RS						Q-OffsetRange				DEFAULT dB0,
	rsrqOffsetCSI-RS						Q-OffsetRange				DEFAULT dB0,
	sinrOffsetCSI-RS						Q-OffsetRange				DEFAULT dB0
}

SSB-ToMeasure ::=			CHOICE {
	
	shortBitmap							BIT STRING (SIZE (4)),
	
	mediumBitmap						BIT STRING (SIZE (8)),
	
	longBitmap							BIT STRING (SIZE (64))
}


ThresholdNR ::=							SEQUENCE{
	thresholdRSRP							RSRP-Range					OPTIONAL,
	thresholdRSRQ						RSRQ-Range					OPTIONAL,
	thresholdSINR						SINR-Range					OPTIONAL
}

CellsToAddModList ::=					SEQUENCE (SIZE (1..maxNrofCellMeas)) OF CellsToAddMod

CellsToAddMod ::=						SEQUENCE {
	physCellId								PhysCellId,
	cellIndividualOffset					Q-OffsetRangeList
}

BlackCellsToAddModList ::=				SEQUENCE (SIZE (1..maxNrofPCI-Ranges)) OF BlackCellsToAddMod

BlackCellsToAddMod ::=					SEQUENCE {
	pci-RangeIndex							PCI-RangeIndex,		
	pci-Range								PCI-Range
}


WhiteCellsToAddModList ::=				SEQUENCE (SIZE (1..maxNrofPCI-Ranges)) OF WhiteCellsToAddMod

WhiteCellsToAddMod ::=					SEQUENCE {
	pci-RangeIndex							PCI-RangeIndex,
	pci-Range							PCI-Range
}





MeasObjectToAddModList ::=					SEQUENCE (SIZE (1..maxNrofObjectId)) OF MeasObjectToAddMod

MeasObjectToAddMod ::=						SEQUENCE {
	measObjectId								MeasObjectId,
	measObject									CHOICE {
		measObjectNR								MeasObjectNR,
		...
	}
}





MeasResults ::=								SEQUENCE {
	measId										MeasId,
	measResultServingFreqList					MeasResultServFreqList,
	measResultNeighCells						CHOICE {
		measResultListNR							MeasResultListNR,
		...
	}																														OPTIONAL,
	...
}

MeasResultServFreqList ::=					SEQUENCE (SIZE (1..maxNrofServingCells)) OF MeasResultServFreq

MeasResultServFreq ::=						SEQUENCE {
	servFreqId									ServCellIndex,																
	measResultServingCell						MeasResultNR,
	measResultBestNeighCell						MeasResultNR,
	...															
}

MeasResultListNR ::=						SEQUENCE (SIZE (1..maxCellReport)) OF MeasResultNR

MeasResultNR ::=							SEQUENCE {
	physCellId									PhysCellId																	OPTIONAL,
	
	cgi-Info									ENUMERATED {ffsTypeAndValue}												OPTIONAL,
	measResult									SEQUENCE {
		cellResults									SEQUENCE{
			resultsSSB-Cell								MeasQuantityResults													OPTIONAL,
			resultsCSI-RS-Cell							MeasQuantityResults													OPTIONAL
		},
		rsIndexResults								SEQUENCE{
			resultsSSB-Indexes							ResultsPerSSB-IndexList												OPTIONAL, 
			resultsCSI-RS-Indexes						ResultsPerCSI-RS-IndexList											OPTIONAL
		}																													OPTIONAL
	},
	...
}


MeasQuantityResults ::= 		SEQUENCE {
	rsrp							RSRP-Range													OPTIONAL,
	rsrq							RSRQ-Range													OPTIONAL,
	sinr							SINR-Range													OPTIONAL
}

ResultsPerSSB-IndexList::= 				SEQUENCE (SIZE (1..maxNrofSSBs)) OF ResultsPerSSB-Index

ResultsPerSSB-Index ::= 					SEQUENCE {
	ssb-Index									SSB-Index,
	ssb-Results									MeasQuantityResults							OPTIONAL
}

ResultsPerCSI-RS-IndexList::= 				SEQUENCE (SIZE (1..maxNrofCSI-RS)) OF ResultsPerCSI-RS-Index

ResultsPerCSI-RS-Index ::= 					SEQUENCE {
	csi-RS-Index								CSI-RS-Index,
	csi-RS-Results								MeasQuantityResults							OPTIONAL
}





MeasResultSCG-Failure ::= 			SEQUENCE {
	measResultServFreqList					MeasResultServFreqList2NR,
	measResultNeighCells						MeasResultList2NR,
	...
}

MeasResultServFreqList2NR ::=			SEQUENCE (SIZE (1..maxNrofServingCells)) OF MeasResultServFreq2NR

MeasResultServFreq2NR ::=				SEQUENCE {
	ssbFrequency							ARFCN-ValueNR			OPTIONAL,
	refFreqCSI-RS							ARFCN-ValueNR			OPTIONAL,
	measResultServingCell					MeasResultNR,
	measResultBestNeighCell					MeasResultNR		OPTIONAL
}

MeasResultList2NR ::=					SEQUENCE (SIZE (1..maxFreq)) OF MeasResult2NR

MeasResult2NR ::=						SEQUENCE {	
	ssbFrequency							ARFCN-ValueNR			OPTIONAL,
	refFreqCSI-RS							ARFCN-ValueNR			OPTIONAL,
	measResultListNR						MeasResultListNR
}





MeasResultCellListSFTD ::=			SEQUENCE (SIZE (1..maxCellSFTD)) OF MeasResultCellSFTD

MeasResultCellSFTD ::=	SEQUENCE {
	physCellId							PhysCellId,
	sfn-OffsetResult					INTEGER (0..1023),
	frameBoundaryOffsetResult			INTEGER (-30720..30719),
	rsrp-Result							RSRP-Range						OPTIONAL
}





MultiFrequencyBandListNR ::= 		SEQUENCE (SIZE (1..maxNrofMultiBands)) OF FreqBandIndicatorNR




NZP-CSI-RS-ResourceSet ::= 		SEQUENCE {
	nzp-CSI-ResourceSetId					NZP-CSI-RS-ResourceSetId,	

	
	
	
	nzp-CSI-RS-Resources						SEQUENCE (SIZE (1..maxNrofNZP-CSI-RS-ResourcesPerSet)) OF NZP-CSI-RS-ResourceId,

	
	
	
	
	
	repetition									ENUMERATED { on, off }				OPTIONAL,

	
	
	
	aperiodicTriggeringOffset			 		INTEGER(0..4)																		OPTIONAL,	 -- Need S

	
	
	trs-Info								ENUMERATED {true}																OPTIONAL,
	...
}




NZP-CSI-RS-ResourceSetId ::= INTEGER (0..maxNrofNZP-CSI-RS-ResourceSets-1)




NZP-CSI-RS-Resource ::=		SEQUENCE {
	nzp-CSI-RS-ResourceId				NZP-CSI-RS-ResourceId,

	
	resourceMapping							CSI-RS-ResourceMapping,
	
	powerControlOffset						INTEGER(-8..15),
	
	powerControlOffsetSS					ENUMERATED{db-3, db0, db3, db6}								OPTIONAL,	
	
	scramblingID							ScramblingId,

	
	
	periodicityAndOffset					CSI-ResourcePeriodicityAndOffset							OPTIONAL,  --Cond PeriodicOrSemiPersistent

	
	
	
	qcl-InfoPeriodicCSI-RS						TCI-StateId												OPTIONAL,  --Cond Periodic
	...
}




NZP-CSI-RS-ResourceId ::= 					INTEGER (0..maxNrofNZP-CSI-RS-Resources-1)





P-Max ::=				INTEGER (-30..33)





PCI-List ::=						SEQUENCE (SIZE (1..maxNrofCellMeas)) OF PhysCellId





PCI-Range ::=				SEQUENCE {
	start							PhysCellId,
	range							ENUMERATED {
										n4, n8, n12, n16, n24, n32, n48, n64, n84,
										n96, n128, n168, n252, n504, n1008,
										spare1} 					OPTIONAL	 -- Need Nss
}





PCI-RangeIndex ::=						INTEGER (1..maxNrofPCI-Ranges)






PCI-RangeIndexList ::=						SEQUENCE (SIZE (1..maxNrofPCI-Ranges)) OF PCI-RangeIndex





PDCCH-Config ::= 						SEQUENCE {
	
	
	controlResourceSetToAddModList			SEQUENCE(SIZE (1..3)) OF ControlResourceSet 		OPTIONAL,
	controlResourceSetToReleaseList			SEQUENCE(SIZE (1..3)) OF ControlResourceSetId			OPTIONAL,

	
	
	searchSpacesToAddModList				SEQUENCE(SIZE (1..10)) OF SearchSpace						OPTIONAL,
	searchSpacesToReleaseList				SEQUENCE(SIZE (1..10)) OF SearchSpaceId						OPTIONAL,

	
	
	
	downlinkPreemption						SetupRelease { DownlinkPreemption }															OPTIONAL,	 -- Need M

	

	
	slotFormatIndicator						SetupRelease { SlotFormatIndicator }															OPTIONAL,	 -- Need M
	
	tpc-PUSCH								SetupRelease { PUSCH-TPC-CommandConfig }							OPTIONAL,    -- Need M

	
	tpc-PUCCH								SetupRelease { PUCCH-TPC-CommandConfig }							OPTIONAL,    -- Cond PUCCH-CellOnly

	...
}





PDCCH-ConfigCommon ::=					SEQUENCE {

	
	
	
	
	commonControlResourcesSets					SEQUENCE (SIZE(1..2)) OF ControlResourceSet							OPTIONAL, 	 -- Need R

	
	commonSearchSpaces							SEQUENCE (SIZE(1..4)) OF SearchSpace								OPTIONAL,	 -- Need R

	
	
	
	searchSpaceSIB1								SearchSpaceId														OPTIONAL,	 -- Need R
	
	
	
	searchSpaceOtherSystemInformation			SearchSpaceId														OPTIONAL,	 -- Need R
	
	
	
	pagingSearchSpace							SearchSpaceId														OPTIONAL, 	 -- Need R

	
	
	
	ra-ControlResourceSet					ControlResourceSetId																OPTIONAL, 	 -- Need S
	
	
	ra-SearchSpace							SearchSpaceId																	OPTIONAL, 	 -- Need R
	...

}





PDCP-Config ::=			SEQUENCE {
	drb						SEQUENCE {
		discardTimer			ENUMERATED {ms10, ms20, ms30, ms40, ms50, ms60, ms75, ms100, ms150, ms200, ms250, ms300, ms500, ms750, ms1500, infinity} 													OPTIONAL,  -- Cond Setup
		pdcp-SN-SizeUL			ENUMERATED {len12bits, len18bits}				OPTIONAL,  -- Cond Setup2
		pdcp-SN-SizeDL			ENUMERATED {len12bits, len18bits}				OPTIONAL,  -- Cond Setup2
		headerCompression		CHOICE {
			notUsed					NULL,
			rohc					SEQUENCE {
				maxCID					INTEGER (1..16383)				DEFAULT 15,
				profiles				SEQUENCE {
					profile0x0001			BOOLEAN,
					profile0x0002			BOOLEAN,
					profile0x0003			BOOLEAN,
					profile0x0004			BOOLEAN,
					profile0x0006			BOOLEAN,
					profile0x0101			BOOLEAN,
					profile0x0102			BOOLEAN,
					profile0x0103			BOOLEAN,
					profile0x0104			BOOLEAN
				},
				drb-ContinueROHC			BOOLEAN 
			},
			uplinkOnlyROHC			SEQUENCE {
				maxCID					INTEGER (1..16383)				DEFAULT 15,
				profiles				SEQUENCE {
					profile0x0006			BOOLEAN
				},
				drb-ContinueROHC			BOOLEAN 
			},
			...
		},
		integrityProtection		ENUMERATED { enabled }														OPTIONAL,	 -- Cond ConnectedTo5GC
		statusReportRequired	ENUMERATED { true }															OPTIONAL,	 -- Cond Rlc-AM
		outOfOrderDelivery		BOOLEAN
	}																											OPTIONAL,	 -- Cond DRB
	
	moreThanOneRLC			SEQUENCE {
		primaryPath				SEQUENCE {
			cellGroup				CellGroupId											OPTIONAL,	 -- Need R
			logicalChannel			LogicalChannelIdentity								OPTIONAL	 -- Need R
		},
		ul-DataSplitThreshold	UL-DataSplitThreshold 									OPTIONAL,  -- Cond SplitBearer						
		pdcp-Duplication			ENUMERATED { true }													OPTIONAL	 -- Need R
	}																										OPTIONAL,  -- Cond MoreThanOneRLC

	t-Reordering				ENUMERATED {
									ms0, ms1, ms2, ms4, ms5, ms8, ms10, ms15, ms20, ms30, ms40, ms50, ms60, ms80, ms100, ms120, ms140, ms160, ms180, ms200, ms220, 
									ms240, ms260, ms280, ms300,	ms500, ms750, ms1000, ms1250, ms1500, ms1750, ms2000, ms2250, ms2500, ms2750,
									ms3000, spare28, spare27, spare26, spare25, spare24, spare23, spare22, spare21, spare20,
									spare19, spare18, spare17, spare16, spare15, spare14, spare13, spare12, spare11, spare10, spare09,
									spare08, spare07, spare06, spare05, spare04, spare03, spare02, spare01 }		OPTIONAL,  -- Need S

	
	...
}

UL-DataSplitThreshold ::= ENUMERATED { 
											b0, b100, b200, b400, b800, b1600, b3200, b6400, b12800, b25600, b51200, b102400, b204800, 
											b409600, b819200, b1228800, b1638400, b2457600, b3276800, b4096000, b4915200, b5734400, 
											b6553600, infinity, spare8, spare7, spare6, spare5, spare4, spare3, spare2, spare1}





PDSCH-Config ::= 						SEQUENCE {
	
	
	
	dataScramblingIdentityPDSCH			INTEGER (0..1007)															OPTIONAL,

	
	dmrs-DownlinkForPDSCH-MappingTypeA			SetupRelease { DMRS-DownlinkConfig }										OPTIONAL,	 -- Need M
	
	dmrs-DownlinkForPDSCH-MappingTypeB			SetupRelease { DMRS-DownlinkConfig } 							OPTIONAL,	 -- Need M


	
	
	
	tci-StatesToAddModList					SEQUENCE (SIZE(1..maxNrofTCI-States)) OF TCI-State					OPTIONAL,	 -- Need N
	tci-StatesToReleaseList					SEQUENCE (SIZE(1..maxNrofTCI-States)) OF TCI-StateId						OPTIONAL,	 -- Need N

	
	
	vrb-ToPRB-Interleaver					ENUMERATED {n2, n4},

	
	
	resourceAllocation						ENUMERATED { resourceAllocationType0, 
resourceAllocationType1, 
dynamicSwitch},

	
	
	pdsch-AllocationList			SEQUENCE (SIZE(1..maxNrofDL-Allocations)) OF PDSCH-TimeDomainResourceAllocation		OPTIONAL,	 -- Need R
	
	
	pdsch-AggregationFactor					ENUMERATED { n2, n4, n8 }													OPTIONAL,	 -- Need S

	
	
	

	rateMatchPatternToAddModList			SEQUENCE (SIZE (1..maxNrofRateMatchPatterns)) OF RateMatchPattern											OPTIONAL,  -- Need N
	rateMatchPatternToReleaseList			SEQUENCE (SIZE (1..maxNrofRateMatchPatterns)) OF RateMatchPatternId		OPTIONAL,  -- Need N

	
	
	rateMatchPatternGroup1					SEQUENCE (SIZE (1..maxNrofRateMatchPatterns)) OF RateMatchPatternId		OPTIONAL,  -- Need R
	
	
	rateMatchPatternGroup2					SEQUENCE (SIZE (1..maxNrofRateMatchPatterns)) OF RateMatchPatternId		OPTIONAL,  -- Need R


	
	rbg-Size								ENUMERATED {config1, config2},

	
	mcs-Table								ENUMERATED {qam64, qam256},

	
	maxNrofCodeWordsScheduledByDCI			ENUMERATED {n1, n2}															OPTIONAL, 	 -- Need R


	
	
	
	prb-BundlingType					CHOICE {
		static									SEQUENCE {
			bundleSize								ENUMERATED { n4, wideband }											OPTIONAL	 -- Need S
		},
		dynamic 								SEQUENCE {
			bundleSizeSet1							ENUMERATED { n4, wideband, n2-wideband, n4-wideband }				OPTIONAL,	 -- Need S
			bundleSizeSet2							ENUMERATED { n4, wideband }											OPTIONAL	 -- Need S
		}
	},

	
	
	zp-CSI-RS-ResourceToAddModList			SEQUENCE (SIZE (1..maxNrofZP-CSI-RS-Resources)) OF ZP-CSI-RS-Resource	OPTIONAL,	 -- Need N
	zp-CSI-RS-ResourceToReleaseList			SEQUENCE (SIZE (1..maxNrofZP-CSI-RS-Resources)) OF ZP-CSI-RS-ResourceId	OPTIONAL,	 -- Need M

	
	
	
	
	aperiodic-ZP-CSI-RS-ResourceSetsToAddModList	SEQUENCE (SIZE (1..maxNrofZP-CSI-RS-Sets)) OF ZP-CSI-RS-ResourceSet		OPTIONAL,	 -- Need N
	aperiodic-ZP-CSI-RS-ResourceSetsToReleaseList	SEQUENCE (SIZE (1..maxNrofZP-CSI-RS-Sets)) OF ZP-CSI-RS-ResourceSetId	OPTIONAL,	 -- Need N
	
	
	
	
	
	sp-ZP-CSI-RS-ResourceSetsToAddModList	SEQUENCE (SIZE (1..maxNrofZP-CSI-RS-Sets)) OF ZP-CSI-RS-ResourceSet		OPTIONAL,	 -- Need N
	sp-ZP-CSI-RS-ResourceSetsToReleaseList	SEQUENCE (SIZE (1..maxNrofZP-CSI-RS-Sets)) OF ZP-CSI-RS-ResourceSetId	OPTIONAL,	 -- Need N

	...
}








PDSCH-ConfigCommon ::=					SEQUENCE {

	
	pdsch-AllocationList			SEQUENCE (SIZE(1..maxNrofDL-Allocations)) OF PDSCH-TimeDomainResourceAllocation			OPTIONAL,	 -- Need R

	...
}





PDSCH-ServingCellConfig ::= 			SEQUENCE {
	
	codeBlockGroupTransmission				SetupRelease { PDSCH-CodeBlockGroupTransmission }						OPTIONAL,	 -- Need M
	
	
	xOverhead								ENUMERATED { xOh6, xOh12, xOh18 }										OPTIONAL,	 -- Need S
	
	
	
	nrofHARQ-ProcessesForPDSCH				ENUMERATED {n2, n4, n6, n10, n12, n16}									OPTIONAL,	 -- Need S
	
	
	pucch-Cell								ServCellIndex															OPTIONAL	,	 -- Cond SCellAddOnly
	...
}

PDSCH-CodeBlockGroupTransmission ::=		SEQUENCE {
	
	maxCodeBlockGroupsPerTransportBlock		ENUMERATED {n2, n4, n6, n8},
	
	codeBlockGroupFlushIndicator			BOOLEAN,
	...
}





PDSCH-TimeDomainResourceAllocation ::= 		SEQUENCE {
	
	
	k0									INTEGER (1..3)																OPTIONAL,	 -- Need S
	
	mappingType							ENUMERATED {typeA, typeB},
	
	
	startSymbolAndLength				BIT STRING (SIZE (7))
}





PhysCellId ::=						INTEGER (0..1007)





PRB-Id ::=						INTEGER (0..maxNrofPhysicalResourceBlocks-1)





PTRS-DownlinkConfig ::= 					SEQUENCE {
	
	
	
	frequencyDensity							SEQUENCE (SIZE (2)) OF INTEGER (1..276)			OPTIONAL,	 -- Need S
	
	
	
	timeDensity									SEQUENCE (SIZE (3)) OF INTEGER (0..29)		OPTIONAL, 	 -- Need S
	
	
	epre-RatioPort1								INTEGER (0..3)															OPTIONAL,	 -- Need S
	
	
	epre-RatioPort2								SEQUENCE (SIZE (1..2)) OF INTEGER (0..3)								OPTIONAL,	 -- Cond TwoPorts
	
	
	resourceElementOffset						ENUMERATED { offset01, offset10, offset11 }							OPTIONAL,	 -- Need S
	...
}





PTRS-UplinkConfig ::= 					SEQUENCE { 

	modeSpecificParameters					CHOICE {
		
		cp-OFDM									SEQUENCE {
			
			
			
			frequencyDensity						SEQUENCE (SIZE (2)) OF INTEGER (1..276)		OPTIONAL,	 -- Need S
			
				
			
			timeDensity								SEQUENCE (SIZE (3)) OF INTEGER (0..29)		OPTIONAL, 	 -- Need S
			
			
			maxNrofPorts								ENUMERATED {n1, n2},
			
			
			resourceElementOffset					ENUMERATED {offset01, offset10, offset11 }			OPTIONAL,	 -- Need S
			
			ptrs-Power								ENUMERATED {p00, p01, p10, p11}
		},
		
		dft-S-OFDM								SEQUENCE {
			
			
			
			
			sampleDensity						SEQUENCE (SIZE (5)) OF INTEGER (1..276),
			
			
			timeDensity							ENUMERATED {d2}														OPTIONAL	 -- Need S
		}
	}																													OPTIONAL,	 -- Cond M
	...
}





PUCCH-Config ::= 						SEQUENCE {
	
	resourceSetToAddModList					SEQUENCE (SIZE (1..maxNrofPUCCH-ResourceSets)) OF PUCCH-ResourceSet				OPTIONAL,	 -- Need N
	resourceSetToReleaseList				SEQUENCE (SIZE (1..maxNrofPUCCH-ResourceSets)) OF PUCCH-ResourceSetId			OPTIONAL,	 -- Need N

	
	
	
	resourceToAddModList					SEQUENCE (SIZE (1..maxNrofPUCCH-Resources)) OF PUCCH-Resource				OPTIONAL,	 -- Need N
	resourceToReleaseList					SEQUENCE (SIZE (1..maxNrofPUCCH-Resources)) OF PUCCH-ResourceId				OPTIONAL,	 -- Need N

	
	format1									SetupRelease { PUCCH-FormatConfig }												OPTIONAL,	 -- Need M
	
	format2									SetupRelease { PUCCH-FormatConfig }												OPTIONAL,	 -- Need M
	
	format3									SetupRelease { PUCCH-FormatConfig }												OPTIONAL,	 -- Need M
	
	format4									SetupRelease { PUCCH-FormatConfig }												OPTIONAL,	 -- Need M

	schedulingRequestResourceToAddModList	SEQUENCE (SIZE (1..maxNrofSR-Resources)) OF SchedulingRequestResourceConfig		OPTIONAL,  -- Need M
	schedulingRequestResourceToReleaseList	SEQUENCE (SIZE (1..maxNrofSR-Resources)) OF SchedulingRequestResourceId			OPTIONAL,  -- Need M

	multi-CSI-PUCCH-ResourceList			SEQUENCE (SIZE (1..2)) OF PUCCH-ResourceId										OPTIONAL, -- Need M

	
	
	dl-DataToUL-ACK							SEQUENCE (SIZE (8)) OF INTEGER (0..15)											OPTIONAL,	 -- Need M

	
	
	
	spatialRelationInfoToAddModList			SEQUENCE (SIZE (1..maxNrofSpatialRelationInfos)) OF PUCCH-SpatialRelationInfo	OPTIONAL,	 -- Need N
	spatialRelationInfoToReleaseList		SEQUENCE (SIZE (1..maxNrofSpatialRelationInfos)) OF PUCCH-SpatialRelationInfoId	OPTIONAL,	 -- Need N

	pucch-PowerControl						PUCCH-PowerControl																OPTIONAL,	 -- Need M
	...
}

PUCCH-FormatConfig ::=					SEQUENCE {
	
	
	interslotFrequencyHopping				ENUMERATED {enabled}														OPTIONAL, 	 -- Need R
	
	
	
	
	additionalDMRS							ENUMERATED {true}															OPTIONAL,	 -- Need R
	
	
	
	
	maxCodeRate								PUCCH-MaxCodeRate															OPTIONAL,	 -- Need R
	
	
	
	
	nrofSlots								ENUMERATED {n2,n4,n8}													OPTIONAL, 	 -- Need S
	
	
	
	pi2PBSK									ENUMERATED {enabled}														OPTIONAL, 	 -- Need R
	
	
	
	
	
	simultaneousHARQ-ACK-CSI				ENUMERATED {true}															OPTIONAL	 -- Need R
}

PUCCH-MaxCodeRate ::= 						ENUMERATED {zeroDot08, zeroDot15, zeroDot25, zeroDot35, zeroDot45, zeroDot60, zeroDot80}

PUCCH-SpatialRelationInfo ::=				SEQUENCE {
	pucch-SpatialRelationInfoId					PUCCH-SpatialRelationInfoId,
	referenceSignal 							CHOICE {
		ssb-Index									SSB-Index,
		csi-RS-Index								NZP-CSI-RS-ResourceId,
		srs											SRS-ResourceId
	},
	pucch-PathlossReferenceRS-Id 				PUCCH-PathlossReferenceRS-Id,
	p0-PUCCH-Id									P0-PUCCH-Id,
	closedLoopIndex								ENUMERATED { i0, i1 }
}

PUCCH-SpatialRelationInfoId ::= 			INTEGER (1..maxNrofSpatialRelationInfos)


PUCCH-ResourceSet ::=							SEQUENCE {
	pucch-ResourceSetId								PUCCH-ResourceSetId,

	
	
	
	
	
	
	resources										SEQUENCE (SIZE (8..maxNrofPUCCH-ResourcesPerSet)) OF PUCCH-ResourceId,

	
	
	
	
	
	maxPayloadMinus1								INTEGER (4..256)														OPTIONAL	 -- Need R
}

PUCCH-ResourceSetId ::=							INTEGER (0..maxNrofPUCCH-ResourceSets-1)

PUCCH-Resource ::= 								SEQUENCE {
	pucch-ResourceId								PUCCH-ResourceId,

	startingPRB										PRB-Id, 
	
	intraSlotFrequencyHopping						ENUMERATED { enabled }													OPTIONAL,	 -- Need R
	
	
	secondHopPRB									PRB-Id																	OPTIONAL,	 -- Need R

	
	format											CHOICE {
		format0											PUCCH-format0,														 -- Cond InFirstSetOnly
		format1											PUCCH-format1,														 -- Cond InFirstSetOnly
		format2											PUCCH-format2,														 -- Cond NotInFirstSet
		format3											PUCCH-format3,														 -- Cond NotInFirstSet
		format4											PUCCH-format4														 -- Cond NotInFirstSet
	}
}

PUCCH-ResourceId ::=							INTEGER (0..maxNrofPUCCH-Resources-1)




PUCCH-format0 ::=								SEQUENCE {
	initialCyclicShift								INTEGER(0..11),
	nrofSymbols										INTEGER (1..2), 
	startingSymbolIndex								INTEGER(0..13) 
}



PUCCH-format1 ::= 								SEQUENCE {
	initialCyclicShift								INTEGER(0..11), 
	nrofSymbols										INTEGER (4..14), 
	startingSymbolIndex								INTEGER(0..10), 
	timeDomainOCC									INTEGER(0..6)
}



PUCCH-format2 ::= 								SEQUENCE {
	nrofPRBs										INTEGER (1..16), 
	nrofSymbols										INTEGER (1..2), 
	startingSymbolIndex								INTEGER(0..13) 
}



PUCCH-format3 ::= 								SEQUENCE {
	
	nrofPRBs										INTEGER (1..16), 
	nrofSymbols										INTEGER (4..14), 
	startingSymbolIndex								INTEGER(0..10) 
}



PUCCH-format4 ::= 								SEQUENCE {
	nrofSymbols										INTEGER (4..14), 
	occ-Length										ENUMERATED {n2,n4}, 
	occ-Index										ENUMERATED {n0,n1,n2,n3},
	startingSymbolIndex								INTEGER(0..10) 
}





PUCCH-ConfigCommon ::=					SEQUENCE {
	
	
	
	
	pucch-ResourceCommon					BIT STRING (SIZE (4))															OPTIONAL,	 -- Need R

	
	
	
	pucch-GroupHopping						ENUMERATED { neither, enable, disable },
	
	
	hoppingId								BIT STRING (SIZE (10))															OPTIONAL, 	 -- Need R

	
	
	p0-nominal								INTEGER (-202..24)																OPTIONAL, 	 -- Need R

	...
}




PUCCH-PowerControl ::= 				SEQUENCE {

	
	deltaF-PUCCH-f0							INTEGER (-16..15)																	OPTIONAL, 	 -- Need R
	
	deltaF-PUCCH-f1							INTEGER (-16..15)																	OPTIONAL, 	 -- Need R
	
	deltaF-PUCCH-f2							INTEGER (-16..15)																	OPTIONAL, 	 -- Need R
	
	deltaF-PUCCH-f3							INTEGER (-16..15)																	OPTIONAL, 	 -- Need R
	
	deltaF-PUCCH-f4							INTEGER (-16..15)																	OPTIONAL, 	 -- Need R

	
	p0-Set								SEQUENCE (SIZE (1..maxNrofPUCCH-P0-PerSet)) OF P0-PUCCH									OPTIONAL,  -- Need M

	
	
	
	
	pathlossReferenceRSs				SEQUENCE (SIZE (1..maxNrofPUCCH-PathlossReferenceRSs)) OF PUCCH-PathlossReferenceRS	OPTIONAL,  -- Need M
	
	
	
	twoPUCCH-PC-AdjustmentStates		ENUMERATED {twoStates}																	OPTIONAL,  -- Need R
	...
}


P0-PUCCH ::=							SEQUENCE {
	p0-PUCCH-Id								P0-PUCCH-Id,
	
	p0-PUCCH-Value							INTEGER (-16..15)
}

P0-PUCCH-Id ::=							INTEGER (1..8)



PUCCH-PathlossReferenceRS ::=					SEQUENCE {
	pucch-PathlossReferenceRS-Id 				PUCCH-PathlossReferenceRS-Id, 
	referenceSignal								CHOICE {
		ssb-Index									SSB-Index,
		csi-RS-Index								NZP-CSI-RS-ResourceId
	}
}




PUCCH-PathlossReferenceRS-Id ::=			INTEGER (0..maxNrofPUCCH-PathlossReferenceRSs-1)





PUCCH-TPC-CommandConfig ::=				SEQUENCE {
	
	tpc-IndexPCell							INTEGER (1..15)													OPTIONAL,	 -- Cond PUCCH-SCell
	
	tpc-IndexPUCCH-SCell					INTEGER (1..15)													OPTIONAL,	 -- Cond PUCCH-SCellOnly
    ...
}





PUSCH-Config ::= 						SEQUENCE {
	
	
	dataScramblingIdentityPUSCH			INTEGER (0..1007)															OPTIONAL,	 -- Need M
	
	txConfig								ENUMERATED {codebook, nonCodebook},

	
	dmrs-UplinkForPUSCH-MappingTypeA		SetupRelease { DMRS-UplinkConfig }											OPTIONAL,	 -- Need M
	
	dmrs-UplinkForPUSCH-MappingTypeB		SetupRelease { DMRS-UplinkConfig }									OPTIONAL,	 -- Need M

	pusch-PowerControl						PUSCH-PowerControl															OPTIONAL,  -- Need M
	
	
	
	frequencyHopping						ENUMERATED {mode1, mode2}													OPTIONAL,	 -- Need S
	
	
	frequencyHoppingOffsetLists				SEQUENCE (SIZE (1..4)) OF INTEGER (1.. maxNrofPhysicalResourceBlocks-1)	OPTIONAL,	 -- Need M
	
	
	resourceAllocation						ENUMERATED { resourceAllocationType0, resourceAllocationType1, dynamicSwitch},

	
	
	pusch-AllocationList					SEQUENCE (SIZE(1..maxNrofUL-Allocations)) OF PUSCH-TimeDomainResourceAllocation	OPTIONAL, 	 -- Need R,
	
	
	pusch-AggregationFactor					ENUMERATED { n2, n4, n8 }													OPTIONAL, 	 -- Need S

	
	
	
	mcs-Table								ENUMERATED {qam256}													OPTIONAL,	 -- Need S
	
	
	
	mcs-TableTransformPrecoder				ENUMERATED { qam256}													OPTIONAL,	 -- Need S
	
	
	transformPrecoder						ENUMERATED {enabled, disabled}												OPTIONAL,	 -- Need S
	
	
	codebookSubset			ENUMERATED {fullyAndPartialAndNonCoherent, partialAndNonCoherent, nonCoherent},
	
	maxRank									INTEGER (1..4),

	
	
	rbg-Size								ENUMERATED { config2}												OPTIONAL,	 -- Need S

	
	
	
	
	uci-OnPUSCH							SetupRelease { UCI-OnPUSCH}									OPTIONAL,  -- Need M
	
	
	vrb-ToPRB-Interleaver					ENUMERATED {n2, n4},
	...
}

UCI-OnPUSCH ::= 						SEQUENCE {
	betaOffsets								CHOICE {
			dynamic									SEQUENCE (SIZE (4)) OF BetaOffsets,
			semiStatic								BetaOffsets
	}																													OPTIONAL,  -- Need M
	
	
	
	scaling						ENUMERATED { f0p5, f0p65, f0p8, f1 }
}





PUSCH-ConfigCommon ::= 					SEQUENCE {
	
	
	
	groupHoppingEnabledTransformPrecoding	ENUMERATED {enabled}															OPTIONAL,	 -- Need R

	
	pusch-AllocationList					SEQUENCE (SIZE(1..maxNrofUL-Allocations)) OF PUSCH-TimeDomainResourceAllocation	OPTIONAL,	 -- Need R

	
	

	
	
	msg3-DeltaPreamble							INTEGER (-1..6)															OPTIONAL,	 -- Need R

	
	
	
	p0-NominalWithGrant						INTEGER (-202..24)																OPTIONAL,	 -- Need R
	...
}





PUSCH-PowerControl ::= 						SEQUENCE {

	
	
	tpc-Accumulation							ENUMERATED { disabled }													OPTIONAL,	 -- Need R

	
	
	msg3-Alpha									Alpha																	OPTIONAL, 	 -- Need S

	
	
	p0-NominalWithoutGrant						INTEGER (-202..24)														OPTIONAL,	 -- Need M,
	
	
	p0-AlphaSets								SEQUENCE (SIZE (1..maxNrofP0-PUSCH-AlphaSets)) OF P0-PUSCH-AlphaSet		OPTIONAL,	 -- Need M,

	
	
	
	
	pathlossReferenceRSToAddModList				SEQUENCE (SIZE (1..maxNrofPUSCH-PathlossReferenceRSs)) OF PUSCH-PathlossReferenceRS	
																														OPTIONAL,	 -- Need N
	pathlossReferenceRSToReleaseList			SEQUENCE (SIZE (1..maxNrofPUSCH-PathlossReferenceRSs)) OF PUSCH-PathlossReferenceRS-Id	
																														OPTIONAL,	 -- Need N

	
	
	
	twoPUSCH-PC-AdjustmentStates				ENUMERATED {twoStates}													OPTIONAL,  -- Need S

	
	
	deltaMCS									ENUMERATED {enabled}													OPTIONAL,  -- Need S

	
	
	sri-PUSCH-MappingToAddModList			SEQUENCE (SIZE (1..maxNrofSRI-PUSCH-Mappings)) OF SRI-PUSCH-PowerControl		OPTIONAL,  -- Need M
	sri-PUSCH-MappingToReleaseList				SEQUENCE (SIZE (1..maxNrofSRI-PUSCH-Mappings)) OF SRI-PUSCH-PowerControlId	OPTIONAL  -- Need M 
}





P0-PUSCH-AlphaSet ::= 						SEQUENCE {
	p0-PUSCH-AlphaSetId 						P0-PUSCH-AlphaSetId,
	
	p0											INTEGER (-16..15)															OPTIONAL,
	
	
	alpha 										Alpha																	OPTIONAL	 -- Need S
}


P0-PUSCH-AlphaSetId ::= 					INTEGER (0..maxNrofP0-PUSCH-AlphaSets-1)



PUSCH-PathlossReferenceRS ::=				SEQUENCE {
	pusch-PathlossReferenceRS-Id 				PUSCH-PathlossReferenceRS-Id, 
	referenceSignal								CHOICE {
		ssb-Index									SSB-Index,
		csi-RS-Index									NZP-CSI-RS-ResourceId
	}
}




PUSCH-PathlossReferenceRS-Id ::=			INTEGER (0..maxNrofPUSCH-PathlossReferenceRSs-1)



SRI-PUSCH-PowerControl ::=					SEQUENCE {
	
	sri-PUSCH-PowerControlId					SRI-PUSCH-PowerControlId,
	
	sri-PUSCH-PathlossReferenceRS-Id 			PUSCH-PathlossReferenceRS-Id,
	
	sri-P0-PUSCH-AlphaSetId 					P0-PUSCH-AlphaSetId,
	
	sri-PUSCH-ClosedLoopIndex					ENUMERATED { i0, i1 }
}

SRI-PUSCH-PowerControlId ::=				INTEGER (0..maxNrofSRI-PUSCH-Mappings-1)


BetaOffsets ::= 							SEQUENCE {
	
	
	betaOffsetACK-Index1						INTEGER(0..31)															OPTIONAL,  -- Need S
	
	
	betaOffsetACK-Index2						INTEGER(0..31)															OPTIONAL,  -- Need S
	
	
	betaOffsetACK-Index3						INTEGER(0..31)															OPTIONAL,  -- Need S
	
	
	betaOffsetCSI-Part1-Index1						INTEGER(0..31)															OPTIONAL,  -- Need S
	
	
	betaOffsetCSI-Part1-Index2						INTEGER(0..31)															OPTIONAL,  -- Need S
	
	
	betaOffsetCSI-Part2-Index1						INTEGER(0..31)															OPTIONAL,  -- Need S
	
	
	betaOffsetCSI-Part2-Index2						INTEGER(0..31)															OPTIONAL  -- Need S
}





PUSCH-ServingCellConfig ::=				SEQUENCE {
	
	codeBlockGroupTransmission				SetupRelease { PUSCH-CodeBlockGroupGransmission	}							OPTIONAL,	 -- Need M
	
	
	rateMatching							ENUMERATED {limitedBufferRM}												OPTIONAL,	 -- Need S
	
	
	xOverhead								ENUMERATED {xoh6, xoh12, xoh18}												OPTIONAL,	 -- Need S
	...
}

PUSCH-CodeBlockGroupGransmission ::=	SEQUENCE {
	
	
	maxCodeBlockGroupsPerTransportBlock		ENUMERATED {n2, n4, n6, n8},
	...
}





PUSCH-TimeDomainResourceAllocation ::= 	SEQUENCE {
	
	
	k2									INTEGER (0..7)																OPTIONAL,	 -- Need S
	
	mappingType							ENUMERATED {typeA, typeB},
	
	
	startSymbolAndLength				BIT STRING (SIZE (7))
}





PUSCH-TPC-CommandConfig ::=			SEQUENCE {
	
	tpc-Index							INTEGER (1..15)															OPTIONAL,	 -- Cond SUL
	
	tpc-IndexSUL						INTEGER (1..15)															OPTIONAL,	 -- Cond SUL-Only
	
	
	targetCell							ServCellIndex															OPTIONAL,	 -- Need S
	...
}




Q-OffsetRange ::=						ENUMERATED {
												dB-24, dB-22, dB-20, dB-18, dB-16, dB-14,
												dB-12, dB-10, dB-8, dB-6, dB-5, dB-4, dB-3,
												dB-2, dB-1, dB0, dB1, dB2, dB3, dB4, dB5,
												dB6, dB8, dB10, dB12, dB14, dB16, dB18,
												dB20, dB22, dB24}




	
QuantityConfig ::=							SEQUENCE {
	quantityConfigNR-List						QuantityConfigNR-List						OPTIONAL,	 -- Need M
	...
}

QuantityConfigNR-List::=						SEQUENCE (SIZE (1..maxNrofQuantityConfig)) OF QuantityConfigNR

QuantityConfigNR::=							SEQUENCE {
	quantityConfigCell							QuantityConfigRS,
	quantityConfigRS-Index						QuantityConfigRS								OPTIONAL	 -- Need M
}

QuantityConfigRS ::=						SEQUENCE {
	
	ssb-FilterConfig				FilterConfig,

	
	cs-RS-FilterConfig				FilterConfig
}

FilterConfig ::=				SEQUENCE {
	filterCoefficientRSRP			FilterCoefficient										DEFAULT fc4,
	filterCoefficientRSRQ			FilterCoefficient										DEFAULT fc4,
	filterCoefficientRS-SINR		FilterCoefficient										DEFAULT fc4
}





RACH-ConfigCommon ::= 				SEQUENCE {
	
	rach-ConfigGeneric			RACH-ConfigGeneric,

	
	
	totalNumberOfRA-Preambles			INTEGER (1..63)																		OPTIONAL,	 -- Need S

	
	
	ssb-perRACH-OccasionAndCB-PreamblesPerSSB	CHOICE { 
		oneEighth								ENUMERATED {n4,n8,n12,n16,n20,n24,n28,n32,n36,n40,n44,n48,n52,n56,n60,n64}, 
		oneFourth								ENUMERATED {n4,n8,n12,n16,n20,n24,n28,n32,n36,n40,n44,n48,n52,n56,n60,n64}, 
		oneHalf									ENUMERATED {n4,n8,n12,n16,n20,n24,n28,n32,n36,n40,n44,n48,n52,n56,n60,n64}, 
		one										ENUMERATED {n4,n8,n12,n16,n20,n24,n28,n32,n36,n40,n44,n48,n52,n56,n60,n64}, 
		two										ENUMERATED {n4,n8,n12,n16,n20,n24,n28,n32}, 
		four									INTEGER (1..16), 
		eight									INTEGER (1..8), 
		sixteen									INTEGER (1..4)
	}																														OPTIONAL,	 -- Need M

	groupBconfigured 					SEQUENCE {
		
		
		ra-Msg3SizeGroupA					ENUMERATED {b56, b144, b208, b256, b282, b480, b640, b800, b1000, spare7, spare6, spare5,
											spare4, spare3, spare2, spare1},
		
		
		messagePowerOffsetGroupB			ENUMERATED { minusinfinity, dB0, dB5, dB8, dB10, dB12, dB15, dB18},
		
		
		numberOfRA-PreamblesGroupA			INTEGER (1..64)
	}																														OPTIONAL,	 -- Need R

	
	ra-ContentionResolutionTimer			ENUMERATED { sf8, sf16, sf24, sf32, sf40, sf48, sf56, sf64},

	
	
	rsrp-ThresholdSSB						RSRP-Range																		OPTIONAL,	 -- Need R
	
	
	
	rsrp-ThresholdSSB-SUL					RSRP-Range																		OPTIONAL,	 -- Need R

	
	
	prach-RootSequenceIndex					CHOICE {
		l839									INTEGER (0..837),
		l139									INTEGER (0..137)
	},

	
	
	msg1-SubcarrierSpacing					SubcarrierSpacing,

	
	restrictedSetConfig						ENUMERATED {unrestrictedSet, restrictedSetTypeA, restrictedSetTypeB},
	
	
	msg3-transformPrecoding					ENUMERATED {enabled}															OPTIONAL,	 -- Need R
	...
}





RACH-ConfigGeneric ::= 			SEQUENCE {
	
	prach-ConfigurationIndex				INTEGER (0..255),
	
	
	msg1-FDM								ENUMERATED {one, two, four, eight},
	
	
	
	msg1-FrequencyStart						INTEGER (0..maxNrofPhysicalResourceBlocks-1),
	
	zeroCorrelationZoneConfig				INTEGER(0..15),
	
	
	
	preambleReceivedTargetPower				INTEGER (-200..-74),
	
	preambleTransMax 						ENUMERATED {n3, n4, n5, n6, n7,	n8, n10, n20, n50, n100, n200},
	
	powerRampingStep						ENUMERATED {dB0, dB2, dB4, dB6},
	
	ra-ResponseWindow						ENUMERATED {sl1, sl2, sl4, sl8, sl10, sl20, sl40, sl80}
}







RACH-ConfigDedicated ::=		SEQUENCE {
	
	cfra-Resources					CFRA-Resources, 
	...
}

CFRA-Resources ::= 				CHOICE {
	ssb								SEQUENCE {
		ssb-ResourceList				SEQUENCE (SIZE(1..maxRA-SSB-Resources)) OF CFRA-SSB-Resource,
		
		
		ra-ssb-OccasionMaskIndex		INTEGER (0..15)
	},
	csirs							SEQUENCE {
		csirs-ResourceList				SEQUENCE (SIZE(1..maxRA-CSIRS-Resources)) OF CFRA-CSIRS-Resource,
		cfra-csirs-DedicatedRACH-Threshold	RSRP-Range
	}
}

CFRA-SSB-Resource ::= 			SEQUENCE {
	
	ssb								SSB-Index,
	
	ra-PreambleIndex				INTEGER (0..63),
	...
}

CFRA-CSIRS-Resource ::= 		SEQUENCE {
	
	csi-RS							CSI-RS-Index,
	
	ra-OccasionList					SEQUENCE (SIZE(1..maxRA-OccasionsPerCSIRS)) OF INTEGER (0..maxRA-Occasions-1),
	
	ra-PreambleIndex				INTEGER (0..63),	
	...
}





RadioBearerConfig ::=					SEQUENCE {
	srb-ToAddModList						SRB-ToAddModList										OPTIONAL,  -- Need N
	srb3-ToRelease							ENUMERATED{true}										OPTIONAL,  -- Need N
	drb-ToAddModList						DRB-ToAddModList										OPTIONAL,  -- Need N
	drb-ToReleaseList						DRB-ToReleaseList										OPTIONAL,  -- Need N
	securityConfig 							SecurityConfig											OPTIONAL,  -- Cond M
	...
}

SRB-ToAddModList ::=					SEQUENCE (SIZE (1..2)) OF SRB-ToAddMod
SRB-ToAddMod ::=						SEQUENCE {
	srb-Identity							SRB-Identity,
	
	reestablishPDCP							ENUMERATED{true}										OPTIONAL, 		 -- Need N
	discardOnPDCP                           ENUMERATED{true}										OPTIONAL,		 -- Need N
	pdcp-Config								PDCP-Config												OPTIONAL,		 -- Cond PDCP
	...
}


DRB-ToAddModList ::=					SEQUENCE (SIZE (1..maxDRB)) OF DRB-ToAddMod
DRB-ToAddMod ::=						SEQUENCE {
	cnAssociation							CHOICE {
		
		eps-BearerIdentity						INTEGER (0..15),												
		
		sdap-Config								SDAP-Config													
	} 										OPTIONAL,  -- Cond DRBSetup
	drb-Identity							DRB-Identity,

	
	reestablishPDCP						ENUMERATED{true}										OPTIONAL, 		 -- Need N
	recoverPDCP							ENUMERATED{true}										OPTIONAL, 		 -- Need N
	pdcp-Config							PDCP-Config												OPTIONAL,		 -- Cond PDCP
	...
}

DRB-ToReleaseList ::=					SEQUENCE (SIZE (1..maxDRB)) OF DRB-Identity


SecurityConfig ::=						SEQUENCE {	
	securityAlgorithmConfig				SecurityAlgorithmConfig									OPTIONAL,	 -- Cond RBTermChange
	keyToUse							ENUMERATED{keNB, s-KgNB}								OPTIONAL,	 -- Cond RBTermChange
	...
}





RadioLinkMonitoringConfig ::=			SEQUENCE {
	
	
	
	
	
	
	
	
	failureDetectionResources				SEQUENCE (SIZE(1..maxNrofFailureDetectionResources)) OF RadioLinkMonitoringRS	OPTIONAL, 	 -- Need M
	
	
	
	
	beamFailureInstanceMaxCount				ENUMERATED {n1, n2, n3, n4, n5, n6, n8, n10}									OPTIONAL,	 -- Need S
	
	
	
	
	beamFailureDetectionTimer      			ENUMERATED {pbfd1, pbfd2, pbfd3, pbfd4, pbfd5, pbfd6, pbfd8, pbfd10}			OPTIONAL,	 -- Need R
	...
}

RadioLinkMonitoringRS ::=				SEQUENCE {
	
	purpose									ENUMERATED {beamFailure, rlf, both},
	
	
	detectionResource						CHOICE {
		ssb-Index								SSB-Index,
		csi-RS-Index							NZP-CSI-RS-ResourceId
	},
	...
}




RateMatchPattern ::= 						SEQUENCE {
	rateMatchPatternId							RateMatchPatternId,

	patternType									CHOICE {
		bitmaps										SEQUENCE {
			
			
			
			resourceBlocks								BIT STRING (SIZE (275)),

			
			
			
			
			symbolsInResourceBlock						CHOICE {
				oneSlot										BIT STRING (SIZE (14)),
				twoSlots									BIT STRING (SIZE (28))
			},

			
			
			
			
			periodicityAndPattern						CHOICE {
				n2											BIT STRING (SIZE (2)), 
				n4											BIT STRING (SIZE (4)), 
				n5											BIT STRING (SIZE (5)), 
				n8											BIT STRING (SIZE (8)), 
				n10											BIT STRING (SIZE (10)), 
				n20											BIT STRING (SIZE (20)), 
				n40											BIT STRING (SIZE (40))
			}																										OPTIONAL, 	 -- Need S
			...
		},
		
		controlResourceSet							ControlResourceSetId
	},
	
	
	
	subcarrierSpacing							SubcarrierSpacing 													OPTIONAL,	 -- Cond CellLevel
	
	mode										ENUMERATED { dynamic, semiStatic },
	...
}





RateMatchPatternId ::=						INTEGER (0..maxNrofRateMatchPatterns-1)





RateMatchPatternLTE-CRS ::=				SEQUENCE {
	
	carrierFreqDL							INTEGER (0..16383),
	
	carrierBandwidthDL						ENUMERATED {n6, n15, n25, n50, n75, n100, spare2, spare1},
	
	
	mbsfn-SubframeConfigList				EUTRA-MBSFN-SubframeConfigList						OPTIONAL,	 -- Need M
	
	
	nrofCRS-Ports							ENUMERATED {n1, n2, n4},
	
	
	v-Shift									ENUMERATED {n0, n1, n2, n3, n4, n5}			
}





ReportConfigId ::=							INTEGER (1..maxReportConfigId)





ReportConfigNR ::=							SEQUENCE {
	reportType									CHOICE {
		periodical									PeriodicalReportConfig, 
		eventTriggered								EventTriggerConfig,

		reportCGI									ENUMERATED {ffsTypeAndValue},
		...
	}
}



EventTriggerConfig::=						SEQUENCE {
	eventId										CHOICE {
		eventA1										SEQUENCE {
			a1-Threshold								MeasTriggerQuantity,
			reportOnLeave								BOOLEAN,
			hysteresis									Hysteresis,
			timeToTrigger								TimeToTrigger
		},
		eventA2										SEQUENCE {
			a2-Threshold								MeasTriggerQuantity,
			reportOnLeave								BOOLEAN,
			hysteresis									Hysteresis,
			timeToTrigger								TimeToTrigger
		},
		eventA3										SEQUENCE {
			a3-Offset									MeasTriggerQuantityOffset,
			reportOnLeave								BOOLEAN,
			hysteresis									Hysteresis,
			timeToTrigger								TimeToTrigger,
			useWhiteCellList							BOOLEAN														
		},
		eventA4										SEQUENCE {
			a4-Threshold								MeasTriggerQuantity,
			reportOnLeave								BOOLEAN,
			hysteresis									Hysteresis,
			timeToTrigger								TimeToTrigger,
			useWhiteCellList							BOOLEAN														
		},
		eventA5										SEQUENCE {
			a5-Threshold1								MeasTriggerQuantity,
			a5-Threshold2								MeasTriggerQuantity,
			reportOnLeave								BOOLEAN,
			hysteresis									Hysteresis,
			timeToTrigger								TimeToTrigger,
			useWhiteCellList							BOOLEAN														
		},
		eventA6										SEQUENCE {
			a6-Offset									MeasTriggerQuantityOffset,
			reportOnLeave								BOOLEAN,
			hysteresis									Hysteresis,
			timeToTrigger								TimeToTrigger,
			useWhiteCellList							BOOLEAN														
		},
		...
	},

	rsType										NR-RS-Type,

	
	reportInterval								ReportInterval,
	reportAmount								ENUMERATED {r1, r2, r4, r8, r16, r32, r64, infinity},

	
	reportQuantityCell							MeasReportQuantity,
	maxReportCells								INTEGER (1..maxCellReport),

	
	reportQuantityRsIndexes						MeasReportQuantity													OPTIONAL,	 -- Need M
	maxNrofRSIndexesToReport					INTEGER (1..maxNrofIndexesToReport) 								OPTIONAL,	 -- Need M
	includeBeamMeasurements						BOOLEAN,
	
	reportAddNeighMeas							ENUMERATED {setup}									OPTIONAL,		 -- Need R
	...

}

PeriodicalReportConfig ::=					SEQUENCE {
	rsType										NR-RS-Type,

	
	reportInterval								ReportInterval,
	reportAmount								ENUMERATED {r1, r2, r4, r8, r16, r32, r64, infinity},

	
	reportQuantityCell							MeasReportQuantity,
	maxReportCells								INTEGER (1..maxCellReport),

	
	reportQuantityRsIndexes						MeasReportQuantity													OPTIONAL,	 -- Need R
	maxNrofRsIndexesToReport					INTEGER (1..maxNrofIndexesToReport) 									OPTIONAL,	 -- Need R
	includeBeamMeasurements						BOOLEAN,
	useWhiteCellList							BOOLEAN,
	...

}

NR-RS-Type ::= ENUMERATED {ssb, csi-rs}

MeasTriggerQuantity ::=						CHOICE {
	rsrp										RSRP-Range,
	rsrq										RSRQ-Range,
	sinr										SINR-Range
}

MeasTriggerQuantityOffset ::=				CHOICE {
	rsrp										INTEGER (-30..30),														
	rsrq										INTEGER (-30..30),														
	sinr										INTEGER (-30..30)														
}

			
MeasReportQuantity ::=						SEQUENCE {
	rsrp										BOOLEAN,
	rsrq										BOOLEAN,
	sinr										BOOLEAN
}






ReportConfigToAddModList ::=		SEQUENCE (SIZE (1..maxReportConfigId)) OF ReportConfigToAddMod

ReportConfigToAddMod ::=	SEQUENCE {
	reportConfigId						ReportConfigId,
	reportConfig						CHOICE {
		reportConfigNR						ReportConfigNR,
		...
	}
}




ReportInterval ::=					ENUMERATED {ms120, ms240, ms480, ms640, ms1024, ms2048, ms5120, ms10240, ms20480, ms40960, min1,
													min6, min12, min30 }




RLC-Config ::=						CHOICE {
	am									SEQUENCE {
		ul-AM-RLC							UL-AM-RLC,
		dl-AM-RLC							DL-AM-RLC
	},
	um-Bi-Directional					SEQUENCE {
		ul-UM-RLC							UL-UM-RLC,
		dl-UM-RLC							DL-UM-RLC
	},
	um-Uni-Directional-UL				SEQUENCE {
		ul-UM-RLC							UL-UM-RLC
	},
	um-Uni-Directional-DL				SEQUENCE {
		dl-UM-RLC							DL-UM-RLC
	},
	...
}

UL-AM-RLC ::=						SEQUENCE {
	sn-FieldLength						SN-FieldLengthAM,
	t-PollRetransmit					T-PollRetransmit,
	pollPDU								PollPDU,
	pollByte							PollByte,
	maxRetxThreshold					ENUMERATED { t1, t2, t3, t4, t6, t8, t16, t32 }
}

DL-AM-RLC ::=						SEQUENCE {
	sn-FieldLength						SN-FieldLengthAM,
	t-Reassembly						T-Reassembly,
	t-StatusProhibit					T-StatusProhibit
}

UL-UM-RLC ::=						SEQUENCE {
	sn-FieldLength						SN-FieldLengthUM
}

DL-UM-RLC ::=						SEQUENCE {
	sn-FieldLength						SN-FieldLengthUM,
	t-Reassembly						T-Reassembly
}

T-PollRetransmit ::=				ENUMERATED {
										ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, ms800, ms1000,
										ms2000, ms4000, spare5, spare4, spare3,
										spare2, spare1}


PollPDU ::=							ENUMERATED {
										p4, p8, p16, p32, p64, p128, p256, p512, p1024, p2048, p4096, p6144, p8192, p12288, p16384, p20480,
										p24576, p28672, p32768, p40960, p49152, p57344, p65536, infinity, spare8, spare7, spare6, spare5, spare4,
										spare3, spare2, spare1}

PollByte ::=						ENUMERATED {
										kB1, kB2, kB5, kB8, kB10, kB15, kB25, kB50, kB75,
										kB100, kB125, kB250, kB375, kB500, kB750, kB1000,
										kB1250, kB1500, kB2000, kB3000, kB4000, kB4500,
										kB5000, kB5500, kB6000, kB6500, kB7000, kB7500,
										mB8, mB9, mB10, mB11, mB12, mB13, mB14, mB15,
										mB16, mB17, mB18, mB20, mB25, mB30, mB40, infinity,
										spare20, spare19, spare18, spare17, spare16,
										spare15, spare14, spare13, spare12, spare11,
										spare10, spare9, spare8, spare7, spare6, spare5,
										spare4, spare3, spare2, spare1}

T-Reassembly ::=					ENUMERATED {
										ms0, ms5, ms10, ms15, ms20, ms25, ms30, ms35,
										ms40, ms45, ms50, ms55, ms60, ms65, ms70,
										ms75, ms80, ms85, ms90, ms95, ms100, ms110,
										ms120, ms130, ms140, ms150, ms160, ms170,
										ms180, ms190, ms200, spare1}

T-StatusProhibit ::=				ENUMERATED {
										ms0, ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, ms800, ms1000,
										ms1200, ms1600, ms2000, ms2400, spare2, spare1}

SN-FieldLengthUM ::=				ENUMERATED {size6, size12}
SN-FieldLengthAM ::=				ENUMERATED {size12, size18}





RLF-TimersAndConstants ::= 			SEQUENCE {
	t310								ENUMERATED {ms0, ms50, ms100, ms200, ms500, ms1000, ms2000, ms4000, ms6000},
	n310								ENUMERATED {n1, n2, n3, n4, n6, n8, n10, n20},
	n311								ENUMERATED {n1, n2, n3, n4, n5, n6, n8, n10},
	...
}





RNTI-Value ::=						INTEGER (0..65535)





RSRP-Range ::=						INTEGER(0..124)





RSRQ-Range ::=						INTEGER(0..127)






SCellIndex ::=						INTEGER (1..31)


 


SchedulingRequestConfig ::= 		SEQUENCE {
	schedulingRequestToAddModList		SEQUENCE (SIZE (1..maxNrofSR-ConfigPerCellGroup)) OF SchedulingRequestToAddMod			OPTIONAL,  -- Need N
	schedulingRequestToReleaseList		SEQUENCE (SIZE (1..maxNrofSR-ConfigPerCellGroup)) OF SchedulingRequestId				OPTIONAL   -- Need N
}

SchedulingRequestToAddMod ::=		SEQUENCE {
	sr-ConfigIndex		SchedulingRequestId,

	sr-ProhibitTimer					ENUMERATED {ms1, ms2, ms4, ms8, ms16, ms32, ms64, ms128}					OPTIONAL,	 -- Need S
	sr-TransMax							ENUMERATED { n4, n8, n16, n32, n64, spare3, spare2, spare1}
}

SchedulingRequestId ::=	INTEGER (0..7)




 


SchedulingRequestResourceConfig ::=			SEQUENCE {
	schedulingRequestResourceId						SchedulingRequestResourceId,
	
	schedulingRequestID								SchedulingRequestId,
	
	
	
	
	
	
	
	
	periodicityAndOffset							CHOICE {
		sym2											NULL,						
		sym6or7											NULL,						
		sl1												NULL,						
		sl2												INTEGER (0..1),
		sl4												INTEGER (0..3),
		sl5												INTEGER (0..4),
		sl8												INTEGER (0..7),
		sl10											INTEGER (0..9),
		sl16											INTEGER (0..15),
		sl20											INTEGER (0..19),
		sl40											INTEGER (0..39),
		sl80											INTEGER (0..79),
		sl160											INTEGER (0..159),
		sl320											INTEGER (0..319),
		sl640											INTEGER (0..639)
	}																														OPTIONAL,	 -- Need M
	
	
	
	
	resource										PUCCH-ResourceId														OPTIONAL	 -- Need M
}





SchedulingRequestResourceId ::=					INTEGER (1..maxNrofSR-Resources)


 


ScramblingId ::=					INTEGER (0..1023)





SCS-SpecificCarrier ::=			SEQUENCE {
	
	
	
	offsetToCarrier				INTEGER (0..2199),
	
	
	
	subcarrierSpacing					SubcarrierSpacing,
	
	
	k0									ENUMERATED {n-6, n0, n6}, 
	
	
	carrierBandwidth					INTEGER (1..maxNrofPhysicalResourceBlocks),
	...
}


 


SDAP-Config ::=						SEQUENCE {
	pdu-Session							PDU-SessionID,

	
	sdap-HeaderDL 						ENUMERATED {present, absent},
	sdap-HeaderUL 						ENUMERATED {present, absent},
	defaultDRB							BOOLEAN,

	
	mappedQoS-FlowsToAdd				SEQUENCE (SIZE (1..maxNrofQFIs)) OF QFI 									OPTIONAL,  -- Need N
	
	mappedQoS-FlowsToRelease			SEQUENCE (SIZE (1..maxNrofQFIs)) OF QFI 									OPTIONAL,  -- Need N
	...
}

QFI ::= 							INTEGER (0..maxQFI)

PDU-SessionID ::= INTEGER (0..255)





SearchSpace ::= 						SEQUENCE {
	
	
	searchSpaceId							SearchSpaceId,

	
	
	
	controlResourceSetId					ControlResourceSetId														OPTIONAL, 	 -- Cond SetupOnly

	
	
	monitoringSlotPeriodicityAndOffset		CHOICE {
		sl1										NULL, 
		sl2										INTEGER (0..1), 
		sl4										INTEGER (0..3), 
		sl5 									INTEGER (0..4),
		sl8										INTEGER (0..7), 
		sl10 									INTEGER (0..9),
		sl16 									INTEGER (0..15),
		sl20 									INTEGER (0..19)
	}																													OPTIONAL,	 -- Cond Setup

	
	
	
	monitoringSymbolsWithinSlot					BIT STRING (SIZE (14))													OPTIONAL, 	 -- Cond Setup

	
	
	
	
	nrofCandidates							SEQUENCE {
		aggregationLevel1						ENUMERATED {n0, n1, n2, n3, n4, n5, n6, n8},
		aggregationLevel2						ENUMERATED {n0, n1, n2, n3, n4, n5, n6, n8},
		aggregationLevel4						ENUMERATED {n0, n1, n2, n3, n4, n5, n6, n8},
		aggregationLevel8						ENUMERATED {n0, n1, n2, n3, n4, n5, n6, n8},
		aggregationLevel16						ENUMERATED {n0, n1, n2, n3, n4, n5, n6, n8}
	}																													OPTIONAL,	 -- Cond Setup

	
	searchSpaceType							CHOICE {
		
		common									SEQUENCE {
			
			
			dci-Format0-0-AndFormat1-0					SEQUENCE {
				...
			}																											OPTIONAL,	 -- Need R
			
			dci-Format2-0								SEQUENCE {
				
				
				
				nrofCandidates-SFI							SEQUENCE {
					aggregationLevel1							ENUMERATED {n1, n2}										OPTIONAL,	 -- Need R
					aggregationLevel2							ENUMERATED {n1, n2}										OPTIONAL,	 -- Need R
					aggregationLevel4							ENUMERATED {n1, n2}										OPTIONAL,	 -- Need R
					aggregationLevel8							ENUMERATED {n1, n2}										OPTIONAL,	 -- Need R
					aggregationLevel16							ENUMERATED {n1, n2}										OPTIONAL	 -- Need R
				},
				...
			}																											OPTIONAL,	 -- Need R
			
			dci-Format2-1								SEQUENCE {
				...
			}																											OPTIONAL,	 -- Need R
			
			dci-Format2-2								SEQUENCE {
				...
			}																											OPTIONAL,	 -- Need R
			
			dci-Format2-3								SEQUENCE {
				
				
				monitoringPeriodicity				ENUMERATED {n1, n2, n4, n5, n8, n10, n16, n20 }						OPTIONAL, 	 -- Cond Setup

				
				
				nrofPDCCH-Candidates				ENUMERATED {n1, n2},
				...
			}																											OPTIONAL	 -- Need R
		},
		
		
		ue-Specific								SEQUENCE {
			
			dci-Formats									ENUMERATED {formats0-0-And-1-0, formats0-1-And-1-1},
			... 
		}
	}																													OPTIONAL	 -- Cond Setup
}




SearchSpaceId ::= 							INTEGER (0..maxNrofSearchSpaces-1)





SecurityAlgorithmConfig ::=			SEQUENCE {
	cipheringAlgorithm					CipheringAlgorithm,
	integrityProtAlgorithm				IntegrityProtAlgorithm			OPTIONAL,	 -- Need R	
	...
}

IntegrityProtAlgorithm ::=			ENUMERATED {
											nia0, nia1, nia2, nia3, spare4, spare3,
											spare2, spare1, ...}

CipheringAlgorithm ::=				ENUMERATED {
											nea0, nea1, nea2, nea3, spare4, spare3,
											spare2, spare1, ...}





ServCellIndex ::=					INTEGER (0..maxNrofServingCells-1)





ServingCellConfig ::=		SEQUENCE {
	

	tdd-UL-DL-ConfigurationDedicated	TDD-UL-DL-ConfigDedicated												OPTIONAL,  -- Cond TDD

	
	initialDownlinkBWP					BWP-DownlinkDedicated													OPTIONAL,	 -- Cond ServCellAdd

	
	downlinkBWP-ToReleaseList			SEQUENCE (SIZE (1..maxNrofBWPs)) OF BWP-Id								OPTIONAL,	 -- Need N
	
	downlinkBWP-ToAddModList			SEQUENCE (SIZE (1..maxNrofBWPs)) OF BWP-Downlink						OPTIONAL, 	 -- Need N

	
	
	
	
	
	
	firstActiveDownlinkBWP-Id			BWP-Id																	OPTIONAL,	 -- Need R

	
	
	
	bwp-InactivityTimer					ENUMERATED {ms2, ms3, ms4, ms5, ms6, ms8, ms10, ms20, ms30, ms40,ms50, ms60, ms80,
													ms100, ms200, ms300, ms500, ms750, ms1280, ms1920, ms2560, spare10, spare9, 
													spare8, spare7, spare6, spare5, spare4, spare3, spare2, spare1 } OPTIONAL,	 --	Need R	

	
	
	
	
	defaultDownlinkBWP-Id				BWP-Id																	OPTIONAL, 	 -- Need M

	uplinkConfig						UplinkConfig															OPTIONAL,	 -- Cond ServCellAdd-UL
	supplementaryUplink					UplinkConfig 															OPTIONAL, 	 -- Cond ServCellAdd-SUL


	
	pdsch-ServingCellConfig				SetupRelease { PDSCH-ServingCellConfig }								OPTIONAL,	 -- Need M
	csi-MeasConfig						SetupRelease { CSI-MeasConfig }											OPTIONAL,	 -- Need M
	
	
	
	carrierSwitching					SetupRelease { SRS-CarrierSwitching	}									OPTIONAL,	 -- Need M
	
	sCellDeactivationTimer				ENUMERATED {ms20, ms40, ms80, ms160, ms200, ms240, ms320, ms400, ms480, ms520, ms640, 
												ms720, ms840, ms1280, spare2,spare1}				OPTIONAL,	 -- Cond ServingCellWithoutPUCCH

	
	crossCarrierSchedulingConfig		CrossCarrierSchedulingConfig											OPTIONAL,	 -- Need M

	
	tag-Id								TAG-Id,
	
	
	
	ue-BeamLockFunction					ENUMERATED {enabled}													OPTIONAL,	 -- Need R

	
	
	pathlossReferenceLinking			ENUMERATED {pCell, sCell}												OPTIONAL		 -- Cond SCellOnly
}

UplinkConfig ::=					SEQUENCE {
	

	
	initialUplinkBWP					BWP-UplinkDedicated														OPTIONAL, 	 -- Cond ServCellAdd

	
	
	uplinkBWP-ToReleaseList				SEQUENCE (SIZE (1..maxNrofBWPs)) OF BWP-Id								OPTIONAL,	 -- Need N
	uplinkBWP-ToAddModList				SEQUENCE (SIZE (1..maxNrofBWPs)) OF BWP-Uplink							OPTIONAL, 	 -- Need N

	
	
	
	
	
	
	firstActiveUplinkBWP-Id				BWP-Id																	OPTIONAL,	 -- Need R

	

	
	pusch-ServingCellConfig				SetupRelease { PUSCH-ServingCellConfig }								OPTIONAL,	 -- Need M
	...
}





ServingCellConfigCommon ::=		SEQUENCE {
	physCellId							PhysCellId													OPTIONAL,  -- Cond HOAndServCellAdd,
	frequencyInfoDL						FrequencyInfoDL												OPTIONAL,  -- Cond InterFreqHOAndServCellAdd
	
	initialDownlinkBWP					BWP-DownlinkCommon											OPTIONAL,	 -- Cond ServCellAdd

	uplinkConfigCommon					UplinkConfigCommon											OPTIONAL,  -- Cond ServCellAdd-UL 
	supplementaryUplinkConfig					UplinkConfigCommon									OPTIONAL,  -- Cond ServCellAdd-SUL


	
	
	
	
	ssb-PositionsInBurst				CHOICE {
		
		shortBitmap							BIT STRING (SIZE (4)),
		
		mediumBitmap						BIT STRING (SIZE (8)),
		
		longBitmap							BIT STRING (SIZE (64))
	}																								OPTIONAL,  -- Need R,
	
	
	ssb-periodicityServingCell			ENUMERATED { ms5, ms10, ms20, ms40, ms80, ms160, spare2, spare1 }			OPTIONAL,	 -- Need S
	
	dmrs-TypeA-Position					ENUMERATED {pos2, pos3},

	
	lte-CRS-ToMatchAround					SetupRelease { RateMatchPatternLTE-CRS } 				OPTIONAL,	 -- Need M

	
	
	
	rateMatchPatternToAddModList			SEQUENCE (SIZE (1..maxNrofRateMatchPatterns)) OF RateMatchPattern		OPTIONAL,  -- Need N
	rateMatchPatternToReleaseList			SEQUENCE (SIZE (1..maxNrofRateMatchPatterns)) OF RateMatchPatternId		OPTIONAL,  -- Need N

	
	
	
	subcarrierSpacing				SubcarrierSpacing												OPTIONAL,  -- Need S
	
	tdd-UL-DL-ConfigurationCommon		TDD-UL-DL-ConfigCommon										OPTIONAL,  -- Cond TDD
	
	
	
	tdd-UL-DL-ConfigurationCommon2		TDD-UL-DL-ConfigCommon										OPTIONAL,  -- Cond TDD
	
	
	ss-PBCH-BlockPower					INTEGER (-60..50),
	...
}

UplinkConfigCommon ::=				SEQUENCE {
	
	frequencyInfoUL						FrequencyInfoUL												OPTIONAL,  -- Cond InterFreqHOAndServCellAdd
	
	
	initialUplinkBWP			BWP-UplinkCommon													OPTIONAL	 -- Cond ServCellAdd
}





SINR-Range ::=						INTEGER(0..127)






SlotFormatCombinationsPerCell ::=								SEQUENCE {
	
	servingCellId								ServCellIndex,

	
	subcarrierSpacing							SubcarrierSpacing,
	
	
	
	
	
	subcarrierSpacing2							SubcarrierSpacing															OPTIONAL,	 -- Need R

	
	
	slotFormatCombinations						SEQUENCE (SIZE (1..maxNrofSlotFormatCombinationsPerSet)) OF SlotFormatCombination	OPTIONAL,

	
	
	positionInDCI							INTEGER(0..maxSFI-DCI-PayloadSize-1)													OPTIONAL,
	...
}

SlotFormatCombination ::= 					SEQUENCE {
	
	
	slotFormatCombinationId						SlotFormatCombinationId,
	
	
	slotFormats									SEQUENCE (SIZE (1..maxNrofSlotFormatsPerCombination)) OF INTEGER (0..255)
}



SlotFormatCombinationId	::=					INTEGER (0..maxNrofSlotFormatCombinationsPerSet-1)





SlotFormatIndicator ::= 		SEQUENCE {
	
	
	sfi-RNTI						RNTI-Value,

	
	
	dci-PayloadSize					INTEGER (1..maxSFI-DCI-PayloadSize),

	
	
	slotFormatCombToAddModList		SEQUENCE (SIZE(1..maxNrofAggregatedCellsPerCellGroup)) OF SlotFormatCombinationsPerCell	OPTIONAL,	 -- Need N
	slotFormatCombToReleaseList		SEQUENCE (SIZE(1..maxNrofAggregatedCellsPerCellGroup)) OF ServCellIndex					OPTIONAL,	 -- Need N
	...
}







SPS-Config ::= 							SEQUENCE {
	
	
	
	periodicity								ENUMERATED {ms10, ms20, ms32, ms40, ms64, ms80, ms128, ms160, ms320, ms640,
														spare6, spare5, spare4, spare3, spare2, spare1},
	
	nrofHARQ-Processes						INTEGER (1..8),
	
	n1PUCCH-AN									PUCCH-Resource																OPTIONAL	 -- Need M
}





SRB-Identity ::=					INTEGER (1..3)





SRS-Config ::= 							SEQUENCE {
	srs-ResourceSetToReleaseList 			SEQUENCE (SIZE(0..maxNrofSRS-ResourceSets)) OF SRS-ResourceSetId			OPTIONAL, 	 -- Need N
	srs-ResourceSetToAddModList 			SEQUENCE (SIZE(0..maxNrofSRS-ResourceSets)) OF SRS-ResourceSet				OPTIONAL, 	 -- Need N

	srs-ResourceToReleaseList 	 			SEQUENCE (SIZE(1..maxNrofSRS-Resources)) OF SRS-ResourceId					OPTIONAL,	 -- Need N
	srs-ResourceToAddModList 	 			SEQUENCE (SIZE(1..maxNrofSRS-Resources)) OF SRS-Resource					OPTIONAL, 	 -- Need N


	
	
	
	tpc-Accumulation							ENUMERATED {disabled}													OPTIONAL,	 -- Need S
	...
}

SRS-ResourceSet ::= 					SEQUENCE {
	
	srs-ResourceSetId						SRS-ResourceSetId,
	
	srs-ResourceIdList						SEQUENCE (SIZE(1..maxNrofSRS-ResourcesPerSet)) OF SRS-ResourceId		OPTIONAL,	 -- Cond Setup

	resourceType							CHOICE {
		aperiodic								SEQUENCE {
			
			
			aperiodicSRS-ResourceTrigger			INTEGER (0..maxNrofSRS-TriggerStates-1),
			
			csi-RS									NZP-CSI-RS-ResourceId,
			
			
			slotOffset								INTEGER (1..8)													OPTIONAL,	 -- Need S
			...
		},
		semi-persistent							SEQUENCE {
			
			
			associatedCSI-RS		NZP-CSI-RS-ResourceId															OPTIONAL,  -- Cond nonCodebook
			...
		},
		periodic								SEQUENCE {
			
			
			associatedCSI-RS		NZP-CSI-RS-ResourceId															OPTIONAL,  -- Cond nonCodebook
			...
		}
	},
	
	
	
	
	usage									ENUMERATED {beamManagement, codebook, nonCodebook, antennaSwitching},

	
	
	alpha									Alpha																		OPTIONAL,  -- Need S
	
	
	p0										INTEGER (-202..24)															OPTIONAL,  -- Cond Setup
	
	
	pathlossReferenceRS						CHOICE {
		ssb-Index								SSB-Index,
		csi-RS-Index							NZP-CSI-RS-ResourceId
	}																													OPTIONAL,  -- Need M
	
	
	
	
	srs-PowerControlAdjustmentStates		ENUMERATED { sameAsFci2, separateClosedLoop}					OPTIONAL,  -- Need S
	...
}

SRS-ResourceSetId ::= 					INTEGER (0..maxNrofSRS-ResourceSets-1)

SRS-Resource ::= 						SEQUENCE {
	srs-ResourceId							SRS-ResourceId,
	nrofSRS-Ports							ENUMERATED {port1, ports2, ports4},
	
	
	
	
	ptrs-PortIndex							ENUMERATED {n0, n1 }														OPTIONAL,	 -- Need R  
	
	transmissionComb						CHOICE {
		n2										SEQUENCE {
			combOffset-n2							INTEGER (0..1),
			
			cyclicShift-n2							INTEGER (0..7)
		}, 
		n4										SEQUENCE {
			combOffset-n4							INTEGER (0..3),
			
			cyclicShift-n4							INTEGER (0..11)
		}
	},
	
	
	
	
	
	resourceMapping							SEQUENCE {
		startPosition							INTEGER (0..5),
		nrofSymbols								ENUMERATED {n1, n2, n4},
		repetitionFactor						ENUMERATED {n1, n2, n4}
	},
	
	
	freqDomainPosition						INTEGER (0..67),
	freqDomainShift							INTEGER (0..268), 
	
	
	freqHopping								SEQUENCE {
		c-SRS									INTEGER (0..63),
		b-SRS									INTEGER (0..3), 
		b-hop									INTEGER (0..3)
	},
	
	
	groupOrSequenceHopping					ENUMERATED { neither, groupHopping, sequenceHopping },
	
	
	
	
	
	resourceType							CHOICE {
		aperiodic								SEQUENCE {
			...
		}, 
		semi-persistent							SEQUENCE {
			
			
			
			
			periodicityAndOffset-sp						SRS-PeriodicityAndOffset,
			...
		},
		periodic								SEQUENCE {
			
			
			
			
			periodicityAndOffset-p						SRS-PeriodicityAndOffset,
			...
		}
	},
	
	
	sequenceId								BIT STRING (SIZE (10)),

	
	
	spatialRelationInfo						CHOICE {
		ssb-Index								SSB-Index,
		csi-RS-Index									NZP-CSI-RS-ResourceId,
		srs										SRS-ResourceId
	}																													OPTIONAL,	 -- Need R
	...
}

SRS-ResourceId ::= 						INTEGER (0..maxNrofSRS-Resources-1)

SRS-PeriodicityAndOffset ::=			CHOICE {
	sl1										NULL, 
	sl2										INTEGER(0..1), 
	sl4										INTEGER(0..3), 
	sl5										INTEGER(0..4), 
	sl8										INTEGER(0..7), 
	sl10									INTEGER(0..9), 
	sl16									INTEGER(0..15), 
	sl20									INTEGER(0..19), 
	sl32									INTEGER(0..31), 
	sl40									INTEGER(0..39), 
	sl64									INTEGER(0..63), 
	sl80									INTEGER(0..79), 
	sl160									INTEGER(0..159), 
	sl320									INTEGER(0..319),
	sl640									INTEGER(0..639),
	sl1280									INTEGER(0..1279),
	sl2560									INTEGER(0..2559)
}




SRS-CarrierSwitching ::=				SEQUENCE {

	
	
	
	srs-SwitchFromServCellIndex				INTEGER (0..31)																OPTIONAL,	 -- Cond Setup

	
	srs-TPC-PDCCH-Group					CHOICE {
		
		
		typeA								SEQUENCE (SIZE (1..32)) OF SRS-TPC-PDCCH-Config,
		
		
		typeB								SRS-TPC-PDCCH-Config
	}																													OPTIONAL, 	 -- Cond Setup

	
	
	srs-CellToSFI						SEQUENCE (SIZE (1..maxNrofServingCells)) OF SlotFormatCombinationsPerCell			OPTIONAL, 	 -- Cond Setup
	
	
	
	monitoringCells		SEQUENCE (SIZE (1..maxNrofServingCells)) OF ServCellIndex						OPTIONAL,	 -- Cond Setup
	...
}


SRS-TPC-PDCCH-Config ::=				SEQUENCE {
	
	
	startingBitOfFormat2-3					INTEGER (1..31)																OPTIONAL, 	 -- Cond Setup
	
	
	
	
	
	fieldTypeFormat2-3						INTEGER (0..1)																OPTIONAL, 	 -- Cond Setup
	
	
	srs-CC-SetIndexlist						SEQUENCE (SIZE(1..4)) OF SRS-CC-SetIndex 									OPTIONAL	 -- Cond Setup
}

SRS-CC-SetIndex ::=						SEQUENCE {
	
	cc-SetIndex								INTEGER (0..3)															OPTIONAL, 	 -- Cond Setup
	
	cc-IndexInOneCC-Set						INTEGER (0..7)															OPTIONAL		 -- Cond Setup
}





SSB-Index ::=								INTEGER (0..63)







SubcarrierSpacing ::= 					ENUMERATED {kHz15, kHz30, kHz60, kHz120, kHz240, spare3, spare2, spare1}






TCI-State ::= 				SEQUENCE {
	tci-StateId					TCI-StateId,
	qcl-Type1					QCL-Info,
	qcl-Type2					QCL-Info																					OPTIONAL,	 -- Need R
	nrofPTRS-Ports				ENUMERATED {n1, n2}																			OPTIONAL,	 -- Need R
	...
}

QCL-Info ::=				SEQUENCE {

	
	cell						ServCellIndex																				OPTIONAL,	 -- Need R

	
	bwp-Id						BWP-Id			OPTIONAL,  -- Cond CSI-RS-Indicated
	 -- Cond NZP-CSI-RS-Indicated: mandatory if csi-rs or csi-RS-for-tracking is included, absent otherwise
	referenceSignal				CHOICE {
		csi-rs						NZP-CSI-RS-ResourceId,
		ssb							SSB-Index,
		
		csi-RS-for-tracking			NZP-CSI-RS-ResourceSetId
	},
	qcl-Type					ENUMERATED {typeA, typeB, typeC, typeD},
	...
}





TCI-StateId ::=				INTEGER (0..maxNrofTCI-States-1)





TDD-UL-DL-ConfigCommon ::=			SEQUENCE {
	
	
	
	
	referenceSubcarrierSpacing			SubcarrierSpacing																	OPTIONAL,
	
	dl-UL-TransmissionPeriodicity		ENUMERATED {ms0p5, ms0p625, ms1, ms1p25, ms2, ms2p5, ms5, ms10}						OPTIONAL,

	
	
	nrofDownlinkSlots					INTEGER (0..maxNrofSlots)																	OPTIONAL,

	
	
	
	nrofDownlinkSymbols					INTEGER (0..maxNrofSymbols-1)															OPTIONAL,	 -- Need R
	
	
	
	nrofUplinkSlots						INTEGER (0..maxNrofSlots)																	OPTIONAL,
	
	
	
	
	nrofUplinkSymbols					INTEGER (0..maxNrofSymbols-1)															OPTIONAL	 -- Need R
}

TDD-UL-DL-ConfigDedicated ::=		SEQUENCE {
	
	
	
	
	slotSpecificConfigurationsToAddModList		SEQUENCE (SIZE (1..maxNrofSlots)) OF TDD-UL-DL-SlotConfig							OPTIONAL,  -- Need N
	slotSpecificConfigurationsToreleaseList		SEQUENCE (SIZE (1..maxNrofSlots)) OF TDD-UL-DL-SlotIndex						OPTIONAL  -- Need N
}

TDD-UL-DL-SlotConfig ::=			SEQUENCE {
	
	slotIndex							TDD-UL-DL-SlotIndex,
		
	
	
	
	symbols								CHOICE {
		allDownlink							NULL,
		allUplink							NULL,
		explicit							SEQUENCE {
			
			
			
			nrofDownlinkSymbols					INTEGER (1..maxNrofSymbols-1)												OPTIONAL,	 -- Need S
			
			
			
			
			nrofUplinkSymbols					INTEGER (1..maxNrofSymbols-1)												OPTIONAL	 -- Need S
		}
	}
}

TDD-UL-DL-SlotIndex ::=				INTEGER (0..maxNrofSlots-1)




TimeToTrigger ::=					ENUMERATED {
										ms0, ms40, ms64, ms80, ms100, ms128, ms160, ms256,
										ms320, ms480, ms512, ms640, ms1024, ms1280, ms2560,
										ms5120}




ZP-CSI-RS-Resource ::=						SEQUENCE {
	
	
	zp-CSI-RS-ResourceId						ZP-CSI-RS-ResourceId,
	
	resourceMapping								CSI-RS-ResourceMapping,
	
	
	periodicityAndOffset						CSI-ResourcePeriodicityAndOffset							OPTIONAL,  --Cond PeriodicOrSemiPersistent

	...
}

ZP-CSI-RS-ResourceId ::=							INTEGER (0..maxNrofZP-CSI-RS-Resources-1)





ZP-CSI-RS-ResourceSet ::= 						SEQUENCE {
	zp-CSI-RS-ResourceSetId							ZP-CSI-RS-ResourceSetId,
	
	zp-CSI-RS-ResourceIdList							SEQUENCE (SIZE(1..maxNrofZP-CSI-RS-ResourcesPerSet)) OF ZP-CSI-RS-ResourceId,
	
	
	resourceType									ENUMERATED {aperiodic, semiPersistent, periodic},
	...
}





ZP-CSI-RS-ResourceSetId ::= 					INTEGER (0..maxNrofZP-CSI-RS-ResourceSets-1)





BandCombinationList ::=	SEQUENCE (SIZE (1..maxBandComb)) OF BandCombination

BandCombination ::= SEQUENCE {
	bandAndDL-ParametersList			BandAndDL-ParametersList,
	bandCombinationsUL					BIT STRING (SIZE (1.. maxBandComb)),
	bandCombinationParametersList		SEQUENCE (SIZE (1..maxBandComb)) OF BandCombinationParameters 	OPTIONAL
}

BandAndDL-ParametersList ::= SEQUENCE (SIZE (1..maxSimultaneousBands)) OF BandAndDL-Parameters

BandAndDL-Parameters ::= CHOICE {
	bandAndDL-ParametersEUTRA	BandAndDL-ParametersEUTRA,
	bandAndDL-ParametersNR		BandAndDL-ParametersNR
}
BandCombinationParameters ::= SEQUENCE {
	ca-ParametersNR					CA-ParametersNR			OPTIONAL,
	mrdc-Parameters					MRDC-Parameters			OPTIONAL
}

CA-ParametersNR ::=	SEQUENCE {
	multipleTimingAdvances		ENUMERATED {supported}				OPTIONAL,

	simultaneousRxTxInterBandCA			ENUMERATED {supported}		OPTIONAL,

	supportedBandwidthCombinationSet	BIT STRING (SIZE (1..32))	OPTIONAL
}

MRDC-Parameters ::=	SEQUENCE {
	singleUL-Transmission		ENUMERATED {supported}		OPTIONAL,

	ul-SharingEUTRA-NR					ENUMERATED {supported}		OPTIONAL,

	ul-SwitchingTimeEUTRA-NR			ENUMERATED {type1, type2}	OPTIONAL,

	simultaneousRxTxInterBandENDC		ENUMERATED {supported}		OPTIONAL,

	asyncIntraBandENDC					ENUMERATED {supported}		OPTIONAL,
	basebandProcesingCombinationMRDC 	BasebandProcessingCombinationMRDC
}

BandAndDL-ParametersEUTRA ::= SEQUENCE {
	bandEUTRA					FreqBandIndicatorEUTRA,
	ca-BandwidthClassDL-EUTRA	CA-BandwidthClassEUTRA		OPTIONAL,
	intraBandContiguousCC-InfoDL-EUTRA-List		SEQUENCE (SIZE (1.. maxNrofServingCellsEUTRA)) OF IntraBandContiguousCC-InfoDL-EUTRA		OPTIONAL
}

BandAndDL-ParametersNR ::= SEQUENCE {
	bandNR						FreqBandIndicatorNR,
	ca-BandwidthClassDL			CA-BandwidthClassNR			OPTIONAL,

	intraBandFreqSeparationDL	FreqSeparationClass					OPTIONAL,
	intraBandContiguousCC-InfoDL-List		SEQUENCE (SIZE (1.. maxNrofServingCells)) OF IntraBandContiguousCC-InfoDL		OPTIONAL
}

IntraBandContiguousCC-InfoDL ::=	SEQUENCE {

	maxNumberMIMO-LayersPDSCH			MIMO-LayersDL					OPTIONAL
}

IntraBandContiguousCC-InfoDL-EUTRA ::=	SEQUENCE {

	mimo-CapabilityDL					ENUMERATED {twoLayers, fourLayers, eightLayers}					OPTIONAL
}





BandCombinationParametersUL-List ::= SEQUENCE (SIZE (1..maxBandComb)) OF BandCombinationParametersUL

BandCombinationParametersUL ::= SEQUENCE (SIZE (1.. maxSimultaneousBands)) OF BandParametersUL

BandParametersUL ::= CHOICE {
	bandParametersUL-EUTRA		BandParametersUL-EUTRA,
	bandParametersUL-NR			BandParametersUL-NR
}

BandParametersUL-EUTRA ::= SEQUENCE {
	ca-BandwidthClassUL-EUTRA	CA-BandwidthClassEUTRA		OPTIONAL,
	intraBandContiguousCC-InfoUL-EUTRA-List		SEQUENCE (SIZE (1.. maxNrofServingCellsEUTRA)) OF IntraBandContiguousCC-InfoUL-EUTRA		OPTIONAL
}

BandParametersUL-NR ::= SEQUENCE {
	ca-BandwidthClassUL			CA-BandwidthClassNR 				OPTIONAL,

	intraBandFreqSeparationUL	FreqSeparationClass					OPTIONAL,
	intraBandContiguousCC-InfoUL-List		SEQUENCE (SIZE (1.. maxNrofServingCells)) OF IntraBandContiguousCC-InfoUL			OPTIONAL
}

IntraBandContiguousCC-InfoUL ::=	SEQUENCE {

	maxNumberMIMO-LayersCB-PUSCH		MIMO-LayersUL					OPTIONAL,
	maxNumberMIMO-LayersNonCB-PUSCH		MIMO-LayersUL					OPTIONAL
}

IntraBandContiguousCC-InfoUL-EUTRA ::=	SEQUENCE {

	mimo-CapabilityUL						ENUMERATED {twoLayers, fourLayers}					OPTIONAL
}





BasebandCombinationParametersUL-List ::= SEQUENCE (SIZE (1..maxBasebandProcComb)) OF BasebandCombinationParametersUL

BasebandCombinationParametersUL ::= SEQUENCE (SIZE (1..maxSimultaneousBands)) OF BasebandParametersPerBandUL

BasebandParametersPerBandUL ::= SEQUENCE {
	ca-BandwidthClassUL				CA-BandwidthClassNR,
	freqRange						ENUMERATED {fr1, fr2},
	basebandParametersPerCC-UL		SEQUENCE (SIZE (1.. maxNrofServingCells)) OF BasebandParametersPerCC-UL
}

BasebandParametersPerCC-UL ::= SEQUENCE {


	supportedSubcarrierSpacingUL				SubcarrierSpacing,


	supportedBandwidthUL		CHOICE {
		fr1							ENUMERATED {mhz5, mhz10, mhz15, mhz20, mhz25, mhz30, mhz40, mhz50, mhz60, mhz80, mhz100},
		fr2							ENUMERATED {mhz50, mhz100, mhz200, mhz400}
	},
	
	scalingFactor0dot75				ENUMERATED {supported}		OPTIONAL,

	maxNumberMIMO-LayersCB-PUSCH		MIMO-LayersUL					OPTIONAL,

	maxNumberMIMO-LayersNonCB-PUSCH		MIMO-LayersUL					OPTIONAL,



	supportedModulationOrderUL					ModulationOrder					OPTIONAL,

	supportedSRS-Resources			SRS-Resources								OPTIONAL,

	srs-TxSwitch					SRS-TxSwitch								OPTIONAL,

	lowLatencyCSI-Feedback				ENUMERATED {supported}					OPTIONAL,

	pusch-DifferentTB-PerSlot		SEQUENCE {
		scs-15kHz						ENUMERATED {upto2, upto7}					OPTIONAL,
		scs-30kHz						ENUMERATED {upto2, upto7}					OPTIONAL,
		scs-60kHz						ENUMERATED {upto2, upto7}					OPTIONAL,
		scs-120kHz						ENUMERATED {upto2, upto7}					OPTIONAL
	}																			OPTIONAL,

	twoPUCCH-Group					ENUMERATED {supported}						OPTIONAL,

	diffNumerologyAcrossPUCCH-Group	ENUMERATED {supported}						OPTIONAL,

	diffNumerologyWithinPUCCH-Group	ENUMERATED {supported}						OPTIONAL,

	crossCarrierScheduling			ENUMERATED {supported}						OPTIONAL,

	supportedNumberTAG				ENUMERATED {n2, n3, n4}						OPTIONAL,

	dynamicSwitchSUL				ENUMERATED {supported}						OPTIONAL,


	simultaneousTxSUL-NonSUL		ENUMERATED {supported}						OPTIONAL,

	searchSpaceSharingCA-UL			ENUMERATED {supported}						OPTIONAL
}





BasebandProcessingCombinationMRDC ::= SEQUENCE (SIZE (1..maxBasebandProcComb)) OF BasebandProcessingCombinationLink

BasebandProcessingCombinationLink ::= SEQUENCE {
	basebandProcessingCombinationIndexMN		BasebandProcessingCombinationIndex, 
	basebandProcessingCombinationLinkedIndexSN	SEQUENCE (SIZE (1..maxBasebandProcComb)) OF BasebandProcessingCombinationIndex
}

BasebandProcessingCombinationIndex ::= INTEGER (1..maxBasebandProcComb)






CA-BandwidthClassNR ::= ENUMERATED {a, b, c, d, e, f, g, h, i, j, k, l, m, n, o, p, q, ...}





CA-BandwidthClassEUTRA ::=	ENUMERATED {a, b, c, d, e, f, ...}





FreqBandIndicatorEUTRA ::=	INTEGER (1..maxBandsEUTRA)





FreqBandList ::=	SEQUENCE (SIZE (1..maxBandsMRDC)) OF FreqBandInformation

FreqBandInformation ::= CHOICE {
	bandEUTRA				FreqBandIndicatorEUTRA,
	bandNR					FreqBandIndicatorNR
}





FreqSeparationClass ::=	ENUMERATED {c1, c2, c3, ...}





MIMO-LayersDL ::=	ENUMERATED {twoLayers, fourLayers, eightLayers}

MIMO-LayersUL ::=	ENUMERATED {oneLayer, twoLayers, fourLayers}





ModulationOrder ::=	ENUMERATED {bpsk-halfpi, bpsk, qpsk, qam16, qam64, qam256}





RAT-Type ::= ENUMERATED {nr, eutra-nr, spare2, spare1, ...}





SupportedBasebandProcessingCombination ::= SEQUENCE (SIZE (1..maxBasebandProcComb)) OF BasebandProcessingCombination

BasebandProcessingCombination ::= SEQUENCE {
	basebandParametersDL			SEQUENCE (SIZE (1..maxSimultaneousBands)) OF BasebandParametersPerBandDL,
	basebandParametersUL				BIT STRING (SIZE (1..maxBasebandProcComb))}

BasebandParametersPerBandDL ::= SEQUENCE {
	ca-BandwidthClassDL			CA-BandwidthClassNR,
	freqRange					ENUMERATED {fr1, fr2},
	basebandParametersPerCC-DL		SEQUENCE (SIZE (1.. maxNrofServingCells)) OF BasebandParametersPerCC-DL
}

BasebandParametersPerCC-DL ::= SEQUENCE {


	supportedSubcarrierSpacingDL				SubcarrierSpacing,


	supportedBandwidthDL		CHOICE {
		fr1							ENUMERATED {mhz5, mhz10, mhz15, mhz20, mhz25, mhz30, mhz40, mhz50, mhz60, mhz80, mhz100},
		fr2							ENUMERATED {mhz50, mhz100, mhz200, mhz400}
	},

	scalingFactor0dot75			ENUMERATED {supported}		OPTIONAL,

	timeDurationForQCL					SEQUENCE {
		scs-60kHz							ENUMERATED {s7, s14, s28}				OPTIONAL,
		sch-120kHz							ENUMERATED {s14, s28}					OPTIONAL
	}																			OPTIONAL,

	scellWithoutSSB					ENUMERATED {supported}						OPTIONAL,

	csi-RS-MeasSCellWithoutSSB		ENUMERATED {supported}						OPTIONAL,

	maxNumberMIMO-LayersPDSCH			MIMO-LayersDL							OPTIONAL,



	supportedModulationOrderDL					ModulationOrder					OPTIONAL,

	srs-AssocCSI-RS					ENUMERATED {supported}						OPTIONAL,

	type1-3-CSS						ENUMERATED {supported}						OPTIONAL,

	pdcchMonitoringAnyOccasions		ENUMERATED {withoutDCI-gap, withDCI-gap}	OPTIONAL,

	ue-SpecificUL-DL-Assignment		ENUMERATED {supported}						OPTIONAL,

	pdsch-DifferentTB-PerSlot		SEQUENCE {
		scs-15kHz						ENUMERATED {upto2, upto7}					OPTIONAL,
		scs-30kHz						ENUMERATED {upto2, upto7}					OPTIONAL,
		scs-60kHz						ENUMERATED {upto2, upto7}					OPTIONAL,
		scs-120kHz						ENUMERATED {upto2, upto7}					OPTIONAL
	}																			OPTIONAL,

	crossCarrierScheduling			ENUMERATED {supported}						OPTIONAL,

	searchSpaceSharingCA-DL			ENUMERATED {supported}						OPTIONAL
}





UE-CapabilityRAT-ContainerList ::=SEQUENCE (SIZE (0.. maxRAT-CapabilityContainers)) OF UE-CapabilityRAT-Container

UE-CapabilityRAT-Container ::= SEQUENCE {
	rat-Type							RAT-Type,
	ue-CapabilityRAT-Container			OCTET STRING
}





UE-MRDC-Capability ::=	SEQUENCE {
	measParametersMRDC					MeasParametersMRDC					OPTIONAL,
	rf-ParametersMRDC					RF-ParametersMRDC,
	phy-ParametersMRDC					Phy-ParametersMRDC					OPTIONAL,
	generalParametersMRDC				GeneralParametersMRDC-XDD-Diff		OPTIONAL,
	fdd-Add-UE-MRDC-Capabilities		UE-MRDC-CapabilityAddXDD-Mode		OPTIONAL,
	tdd-Add-UE-MRDC-Capabilities		UE-MRDC-CapabilityAddXDD-Mode		OPTIONAL,
	fr1-Add-UE-MRDC-Capabilities		UE-MRDC-CapabilityAddFRX-Mode		OPTIONAL,
	fr2-Add-UE-MRDC-Capabilities		UE-MRDC-CapabilityAddFRX-Mode		OPTIONAL,
	lateNonCriticalExtension			OCTET STRING						OPTIONAL,
	nonCriticalExtension				SEQUENCE {}							OPTIONAL
}

UE-MRDC-CapabilityAddXDD-Mode ::=	SEQUENCE {
	phy-ParametersMRDC-XDD-Diff		Phy-ParametersMRDC-XDD-Diff		OPTIONAL,
	measParametersMRDC-XDD-Diff		MeasParametersMRDC-XDD-Diff		OPTIONAL,
	generalParametersMRDC-XDD-Diff		GeneralParametersMRDC-XDD-Diff		OPTIONAL
}

UE-MRDC-CapabilityAddFRX-Mode ::=	SEQUENCE {
	phy-ParametersMRDC-FRX-Diff		Phy-ParametersMRDC-FRX-Diff		OPTIONAL,
	measParametersMRDC-FRX-Diff		MeasParametersMRDC-FRX-Diff
}

RF-ParametersMRDC ::= SEQUENCE {
	supportedBandCombination	BandCombinationList,
	bandCombinationParametersUL-List	BandCombinationParametersUL-List
}

Phy-ParametersMRDC ::= SEQUENCE {
	phy-ParametersMRDC-XDD-Diff		Phy-ParametersMRDC-XDD-Diff		OPTIONAL,
	phy-ParametersMRDC-FRX-Diff		Phy-ParametersMRDC-FRX-Diff		OPTIONAL
}

Phy-ParametersMRDC-XDD-Diff ::=	SEQUENCE {

	dynamicPowerSharing					ENUMERATED {supported}				OPTIONAL,

	tdm-Pattern							ENUMERATED {supported}				OPTIONAL
}
Phy-ParametersMRDC-FRX-Diff ::=	SEQUENCE {

	dynamicPowerSharing					ENUMERATED {supported}				OPTIONAL,

	tdm-Pattern							ENUMERATED {supported}				OPTIONAL
}

MeasParametersMRDC ::= SEQUENCE {
	measParametersMRDC-Common		MeasParametersMRDC-Common,
	measParametersMRDC-XDD-Diff		MeasParametersMRDC-XDD-Diff				OPTIONAL,
	measParametersMRDC-FRX-Diff		MeasParametersMRDC-FRX-Diff
}

MeasParametersMRDC-Common ::=	SEQUENCE {

	independentGapConfig			ENUMERATED {supported}	OPTIONAL 
}

MeasParametersMRDC-XDD-Diff ::=	SEQUENCE {
	sftd-MeasPSCell							ENUMERATED {supported}		OPTIONAL,
	sftd-MeasNR-Cell						ENUMERATED {supported}		OPTIONAL
}

MeasParametersMRDC-FRX-Diff ::=	SEQUENCE {

	simultaneousRxDataSSB-DiffNumerology	ENUMERATED {supported}		OPTIONAL
}

GeneralParametersMRDC-XDD-Diff ::= SEQUENCE {
	splitSRB-WithOneUL-Path				ENUMERATED {supported}		OPTIONAL,
	splitDRB-withUL-Both-MCG-SCG		ENUMERATED {supported}		OPTIONAL,
	srb3									ENUMERATED {supported}		OPTIONAL
}





UE-NR-Capability ::= SEQUENCE {
	pdcp-Parameters					PDCP-Parameters, 
	rlc-Parameters					RLC-Parameters						OPTIONAL,						
	mac-Parameters					MAC-Parameters						OPTIONAL,						 
	phy-Parameters					Phy-Parameters,
	rf-Parameters					RF-Parameters,
	measParameters					MeasParameters						OPTIONAL,
	fdd-Add-UE-NR-Capabilities		UE-NR-CapabilityAddXDD-Mode			OPTIONAL,
	tdd-Add-UE-NR-Capabilities		UE-NR-CapabilityAddXDD-Mode			OPTIONAL,
	fr1-Add-UE-NR-Capabilities		UE-NR-CapabilityAddFRX-Mode			OPTIONAL,
	fr2-Add-UE-NR-Capabilities		UE-NR-CapabilityAddFRX-Mode			OPTIONAL,
	lateNonCriticalExtension		OCTET STRING						OPTIONAL,
	nonCriticalExtension			SEQUENCE {}							OPTIONAL
}

UE-NR-CapabilityAddXDD-Mode ::=	SEQUENCE {
	phy-ParametersXDD-Diff			Phy-ParametersXDD-Diff			OPTIONAL,
	mac-ParametersXDD-Diff			MAC-ParametersXDD-Diff			OPTIONAL,
	measParametersXDD-Diff			MeasParametersXDD-Diff			OPTIONAL
}

UE-NR-CapabilityAddFRX-Mode ::=	SEQUENCE {
	phy-ParametersFRX-Diff			Phy-ParametersFRX-Diff			OPTIONAL,
	measParametersFRX-Diff			MeasParametersFRX-Diff			OPTIONAL
}

Phy-Parameters ::=	SEQUENCE {
	phy-ParametersCommon			Phy-ParametersCommon				OPTIONAL,
	phy-ParametersXDD-Diff			Phy-ParametersXDD-Diff				OPTIONAL,
	phy-ParametersFRX-Diff			Phy-ParametersFRX-Diff				OPTIONAL,
	phy-ParametersFR1				Phy-ParametersFR1					OPTIONAL,
	phy-ParametersFR2				Phy-ParametersFR2					OPTIONAL,
	supportedBasebandProcessingCombination		SupportedBasebandProcessingCombination,
	basebandCombinationParametersUL-List		BasebandCombinationParametersUL-List
}

Phy-ParametersCommon ::=	SEQUENCE {

	csi-RS-CFRA-ForHO					ENUMERATED {supported}						OPTIONAL,

	dynamicPRB-BundlingDL				ENUMERATED {supported}						OPTIONAL,

	sp-CSI-ReportPUCCH					ENUMERATED {supported}						OPTIONAL,

	sp-CSI-ReportPUSCH					ENUMERATED {supported}						OPTIONAL,

	nzp-CSI-RS-IntefMgmt				ENUMERATED {supported}						OPTIONAL,

	type2-SP-CSI-Feedback-LongPUCCH		ENUMERATED {supported}						OPTIONAL,

	multipleCORESET						ENUMERATED {supported}						OPTIONAL,

	dynamicSFI							ENUMERATED {supported}						OPTIONAL,

	precoderGranularityCORESET			ENUMERATED {supported}						OPTIONAL,

	dynamicHARQ-ACK-Codebook			ENUMERATED {supported}						OPTIONAL,

	semiStaticHARQ-ACK-Codebook			ENUMERATED {supported}						OPTIONAL,

	spatialBundlingHARQ-ACK				ENUMERATED {supported}						OPTIONAL,

	dynamicBetaOffsetInd-HARQ-ACK-CSI	ENUMERATED {supported}						OPTIONAL,

	pucch-Repetition-F1-3-4				ENUMERATED {supported}						OPTIONAL,

	ra-Type0-PUSCH						ENUMERATED {supported}						OPTIONAL,

	dynamicSwitchRA-Type0-1-PDSCH		ENUMERATED {supported}						OPTIONAL,

	dynamicSwitchRA-Type0-1-PUSCH		ENUMERATED {supported}						OPTIONAL,

	pdsch-MappingTypeA					ENUMERATED {supported}						OPTIONAL,

	pdsch-MappingTypeB					ENUMERATED {supported}						OPTIONAL,

	interleavingVRB-ToPRB-PDSCH			ENUMERATED {supported}						OPTIONAL,

	interleavingVRB-ToPRB-PUSCH			ENUMERATED {supported}						OPTIONAL,

	interSlotFreqHopping-PUSCH			ENUMERATED {supported}						OPTIONAL,

	type1-PUSCH-RepetitionOneSlot		ENUMERATED {supported}						OPTIONAL,

	type1-PUSCH-RepetitionMultiSlots	ENUMERATED {supported}						OPTIONAL,

	type2-PUSCH-RepetitionOneSlot		ENUMERATED {supported}						OPTIONAL,

	type2-PUSCH-RepetitionMultiSlots	ENUMERATED {supported}						OPTIONAL,

	pusch-RepetitionMultiSlots			ENUMERATED {supported}						OPTIONAL,

	pdsch-RepetitionMultiSlots			ENUMERATED {supported}						OPTIONAL,

	downlinkSPS							ENUMERATED {supported}						OPTIONAL,

	configuredUL-GrantType1				ENUMERATED {supported}						OPTIONAL,

	configuredUL-GrantType2				ENUMERATED {supported}						OPTIONAL,

	pre-EmptIndication-DL				ENUMERATED {supported}						OPTIONAL,

	cbg-TransIndication					BIT STRING (SIZE (2))						OPTIONAL,

	cbg-FlushIndication-DL				ENUMERATED {supported}						OPTIONAL,

	dynamicHARQ-ACK-CodeB-CBG-Retx-DL	ENUMERATED {supported}						OPTIONAL,

	rateMatchingResrcSetSemi-Static		ENUMERATED {supported}						OPTIONAL,

	rateMatchingResrcSetDynamic			ENUMERATED {supported}						OPTIONAL,

	rateMatchingLTE-CRS					ENUMERATED {supported}						OPTIONAL,

	bwp-SwitchingDelay					ENUMERATED {type1, type2}					OPTIONAL
}

Phy-ParametersXDD-Diff ::=	SEQUENCE {

	twoPUCCH-F0-2-ConsecSymbols			ENUMERATED {supported}						OPTIONAL,

	twoDifferentTPC-Loop-PUSCH			ENUMERATED {supported}						OPTIONAL,

	twoDifferentTPC-Loop-PUCCH			ENUMERATED {supported}						OPTIONAL
}

Phy-ParametersFRX-Diff ::=	SEQUENCE {

	oneFL-DMRS-TwoAdditionalDMRS		BIT STRING (SIZE (2))						OPTIONAL,

	twoFL-DMRS							BIT STRING (SIZE (2))						OPTIONAL,

	twoFL-DMRS-TwoAdditionalDMRS		BIT STRING (SIZE (2))						OPTIONAL,

	oneFL-DMRS-ThreeAdditionalDMRS		BIT STRING (SIZE (2))						OPTIONAL,

	supportedDMRS-TypeDL				ENUMERATED {type1, type2}					OPTIONAL,

	supportedDMRS-TypeUL				ENUMERATED {type1, type2}					OPTIONAL,

	semiOpenLoopCSI						ENUMERATED {supported}						OPTIONAL,

	csi-ReportWithoutPMI				ENUMERATED {supported}						OPTIONAL,

	csi-ReportWithCRI					ENUMERATED {supported}						OPTIONAL,

	csi-ReportWithoutCQI				ENUMERATED {supported}						OPTIONAL,

	onePortsPTRS						BIT STRING (SIZE (2))						OPTIONAL,

	twoPUCCH-F0-2-ConsecSymbols			ENUMERATED {supported}						OPTIONAL,

	pucch-F2-WithFH						ENUMERATED {supported}						OPTIONAL,

	pucch-F3-WithFH						ENUMERATED {supported}						OPTIONAL,

	pucch-F4-WithFH						ENUMERATED {supported}						OPTIONAL,

	freqHoppingPUCCH-F0-2				ENUMERATED {notSupported}					OPTIONAL,

	freqHoppingPUCCH-F1-3-4				ENUMERATED {notSupported}					OPTIONAL,

	mux-SR-HARQ-ACK-CSI-PUCCH			ENUMERATED {supported}						OPTIONAL,

	uci-CodeBlockSegmentation			ENUMERATED {supported}						OPTIONAL,

	onePUCCH-LongAndShortFormat			ENUMERATED {supported}						OPTIONAL,

	twoPUCCH-AnyOthersInSlot			ENUMERATED {supported}						OPTIONAL,

	intraSlotFreqHopping-PUSCH			ENUMERATED {supported}						OPTIONAL,

	pusch-LBRM							ENUMERATED {supported}						OPTIONAL,

	pdcch-BlindDetectionCA				ENUMERATED {supported}						OPTIONAL,

	tpc-PUSCH-RNTI						ENUMERATED {supported}						OPTIONAL,

	tpc-PUCCH-RNTI						ENUMERATED {supported}						OPTIONAL,

	tpc-SRS-RNTI						ENUMERATED {supported}						OPTIONAL,

	absoluteTPC-Command					ENUMERATED {supported}						OPTIONAL,

	twoDifferentTPC-Loop-PUSCH			ENUMERATED {supported}						OPTIONAL,

	twoDifferentTPC-Loop-PUCCH			ENUMERATED {supported}						OPTIONAL,

	pusch-HalfPi-BPSK					ENUMERATED {supported}						OPTIONAL,

	pucch-F3-4-HalfPi-BPSK				ENUMERATED {supported}						OPTIONAL,

	oneSymbolGP-TDD						ENUMERATED {supported}						OPTIONAL,

	almostContiguousCP-OFDM-UL			ENUMERATED {supported}						OPTIONAL
}

Phy-ParametersFR1 ::=	SEQUENCE {

	pdcchMonitoringSingleOccasion		ENUMERATED {supported}						OPTIONAL,

	scs-60kHz							ENUMERATED {supported}						OPTIONAL,

	pdsch-256QAM-FR1					ENUMERATED {supported}						OPTIONAL
}

Phy-ParametersFR2 ::=	SEQUENCE {

	calibrationGapPA					ENUMERATED {supported}						OPTIONAL
}

RF-Parameters ::= SEQUENCE {
	supportedBandListNR					SupportedBandListNR,
	supportedBandCombination			BandCombinationList,
	bandCombinationParametersUL-List	BandCombinationParametersUL-List
}

SupportedBandListNR ::=	SEQUENCE (SIZE (1..maxBands)) OF BandNR

BandNR ::=	SEQUENCE {
	bandNR							FreqBandIndicatorNR,

	modifiedMPR-Behaviour			BIT STRING (SIZE (8))						OPTIONAL,


	maxChannelBW-PerCC				ENUMERATED {mhz400}							OPTIONAL,
	mimo-ParametersPerBand			MIMO-ParametersPerBand						OPTIONAL,

	extendedCP						ENUMERATED {supported}						OPTIONAL,

	phaseCoherenceUL				ENUMERATED {supported}						OPTIONAL,

	scellWithoutSSB					ENUMERATED {supported}						OPTIONAL,

	csi-RS-MeasSCellWithoutSSB		ENUMERATED {supported}						OPTIONAL,

	srs-AssocCSI-RS					ENUMERATED {supported}						OPTIONAL,

	type1-3-CSS						ENUMERATED {supported}						OPTIONAL,

	multipleTCI						ENUMERATED {supported}						OPTIONAL,

	pdcchMonitoringAnyOccasions		ENUMERATED {withoutDCI-gap, withDCI-gap}	OPTIONAL,

	ue-SpecificUL-DL-Assignment		ENUMERATED {supported}						OPTIONAL,

	pdsch-DifferentTB-PerSlot		SEQUENCE {
		scs-15kHz						ENUMERATED {upto2, upto7}				OPTIONAL,
		scs-30kHz						ENUMERATED {upto2, upto7}				OPTIONAL,
		scs-60kHz						ENUMERATED {upto2, upto7}				OPTIONAL,
		scs-120kHz						ENUMERATED {upto2, upto7}				OPTIONAL
	}																			OPTIONAL,

	pusch-DifferentTB-PerSlot		SEQUENCE {
		scs-15kHz						ENUMERATED {upto2, upto7}				OPTIONAL,
		scs-30kHz						ENUMERATED {upto2, upto7}				OPTIONAL,
		scs-60kHz						ENUMERATED {upto2, upto7}				OPTIONAL,
		scs-120kHz						ENUMERATED {upto2, upto7}				OPTIONAL
	}																			OPTIONAL,

	bwp-SameNumerology					ENUMERATED {upto2, upto4}				OPTIONAL,

	bwp-DiffNumerology					ENUMERATED {upto4}						OPTIONAL,

	twoPUCCH-Group					ENUMERATED {supported}						OPTIONAL,

	diffNumerologyAcrossPUCCH-Group	ENUMERATED {supported}						OPTIONAL,

	diffNumerologyWithinPUCCH-Group	ENUMERATED {supported}						OPTIONAL,

	crossCarrierScheduling			ENUMERATED {supported}						OPTIONAL,

	supportedNumberTAG				ENUMERATED {n2, n3, n4}						OPTIONAL,


	simultaneousTxSUL-NonSUL		ENUMERATED {supported}						OPTIONAL,

	searchSpaceSharingCA-DL			ENUMERATED {supported}						OPTIONAL,

	searchSpaceSharingCA-UL			ENUMERATED {supported}						OPTIONAL,

	pdsch-256QAM-FR2				ENUMERATED {supported}						OPTIONAL,

	pusch-256QAM					ENUMERATED {supported}						OPTIONAL
}

MIMO-ParametersPerBand ::= SEQUENCE {

	timeDurationForQCL					SEQUENCE {
		scs-60kHz							ENUMERATED {s7, s14, s28}									OPTIONAL,
		sch-120kHz							ENUMERATED {s14, s28}										OPTIONAL
	}																									OPTIONAL,

	maxNumberMIMO-LayersPDSCH			MIMO-LayersDL													OPTIONAL,

	maxNumberMIMO-LayersCB-PUSCH		MIMO-LayersUL													OPTIONAL,

	maxNumberMIMO-LayersNonCB-PUSCH		MIMO-LayersUL													OPTIONAL,

	maxNumberConfiguredTCIstates		ENUMERATED {n4, n8, n16, n32, n64}								OPTIONAL,
	maxNumberActiveTCI-PerCC			ENUMERATED {n1, n2, n4, n8}										OPTIONAL,

	pusch-TransCoherence				ENUMERATED {nonCoherent, partialNonCoherent, fullCoherent}	OPTIONAL,

	beamCorrespondence					ENUMERATED {supported}											OPTIONAL,

	periodicBeamReport					ENUMERATED {supported}											OPTIONAL,

	aperiodicBeamReport					ENUMERATED {supported}											OPTIONAL,

	sp-BeamReportPUCCH					ENUMERATED {supported}											OPTIONAL,

	sp-BeamReportPUSCH					ENUMERATED {supported}											OPTIONAL,

	beamManagementSSB-CSI-RS			BeamManagementSSB-CSI-RS										OPTIONAL,

	maxNumberRxBeam						INTEGER (2..8)													OPTIONAL,

	maxNumberRxTxBeamSwitchDL			SEQUENCE {
		scs-15kHz							ENUMERATED {n4, n7, n14}									OPTIONAL,
		scs-30kHz							ENUMERATED {n4, n7, n14}									OPTIONAL,
		scs-60kHz							ENUMERATED {n4, n7, n14}									OPTIONAL,
		scs-120kHz							ENUMERATED {n4, n7, n14}									OPTIONAL,
		scs-240kHz							ENUMERATED {n4, n7, n14}									OPTIONAL
	}																									OPTIONAL,

	maxNumberNonGroupBeamReporting		ENUMERATED {n1, n2, n4}											OPTIONAL,

	groupBeamReporting					ENUMERATED {supported}											OPTIONAL,

	uplinkBeamManagement				SEQUENCE {
		maxNumberSRS-ResourcePerSet			ENUMERATED {n8, n16, n32},
		maxNumberSRS-ResourceSet			INTEGER (1..8)
	}																									OPTIONAL,

	maxNumberCSI-RS-BFR					INTEGER (1..64)													OPTIONAL,
	maxNumberSSB-BFR					INTEGER (1..64)													OPTIONAL,
	maxNumberCSI-RS-SSB-BFR				INTEGER (1..256)												OPTIONAL,

	twoPortsPTRS						BIT STRING (SIZE (2))											OPTIONAL,

	supportedSRS-Resources			SRS-Resources														OPTIONAL,

	srs-TxSwitch					SRS-TxSwitch														OPTIONAL,

	maxNumberSimultaneousSRS-PerCC		INTEGER (1..4)													OPTIONAL,

	lowLatencyCSI-Feedback				ENUMERATED {supported}											OPTIONAL
}


BeamManagementSSB-CSI-RS ::=	SEQUENCE {
	maxNumberSSB-CSI-RS-ResourceOneTx	ENUMERATED {n8, n16, n32, n64},
	maxNumberSSB-CSI-RS-ResourceTwoTx	ENUMERATED {n0, n4, n8, n16, n32, n64},
	supportedCSI-RS-Density				ENUMERATED {one, three, oneAndThree}
}


SRS-Resources ::=	SEQUENCE {
	maxNumberAperiodicSRS-PerBWP					ENUMERATED {n1, n2, n4, n8, n16},
	maxNumberAperiodicSRS-PerBWP-PerSlot			INTEGER (1..6),
	maxNumberPeriodicSRS-PerBWP						ENUMERATED {n1, n2, n4, n8, n16},
	maxNumberPeriodicSRS-PerBWP-PerSlot				INTEGER (1..6),
	maxNumberSemiPersitentSRS-PerBWP				ENUMERATED {n0, n1, n2, n4, n8, n16},
	maxNumberSP-SRS-PerBWP-PerSlot					INTEGER (0..6),
	maxNumberSRS-Ports-PerResource					ENUMERATED {n1, n2, n4}
}

SRS-TxSwitch ::=	SEQUENCE {
	supportedSRS-TxPortSwitch			ENUMERATED {t1r2, t1r4, t2r4, t1r4-t2r4},
	txSwitchImpactToRx					ENUMERATED {true}								OPTIONAL
}

PDCP-Parameters ::= SEQUENCE {
	supportedROHC-Profiles	SEQUENCE {
		profile0x0000		BOOLEAN, 
		profile0x0001		BOOLEAN, 
		profile0x0002		BOOLEAN,
		profile0x0003		BOOLEAN, 
		profile0x0004		BOOLEAN, 
		profile0x0006		BOOLEAN, 
		profile0x0101		BOOLEAN, 
		profile0x0102		BOOLEAN, 
		profile0x0103		BOOLEAN, 
		profile0x0104		BOOLEAN
	}, 
	maxNumberROHC-ContextSessions	ENUMERATED {cs2, cs4, cs8, cs12, cs16, cs24, cs32, cs48, cs64, cs128, cs256, cs512, cs1024, cs16384, spare2, spare1},	
	uplinkOnlyROHC-Profiles			ENUMERATED {supported}	OPTIONAL, 
	continueROHC-Context			ENUMERATED {supported}	OPTIONAL,
	outOfOrderDelivery				ENUMERATED {supported}	OPTIONAL, 
	shortSN							ENUMERATED {supported} 	OPTIONAL
}

RLC-Parameters ::= SEQUENCE {
	am-WithShortSN					ENUMERATED {supported}	OPTIONAL,
		um-WithShortSN					ENUMERATED {supported}	OPTIONAL, 
		um-WIthLongSN					ENUMERATED {supported}	OPTIONAL
}

MAC-Parameters ::= SEQUENCE {
	mac-ParametersCommon			MAC-ParametersCommon	OPTIONAL,
	mac-ParametersXDD-Diff			MAC-ParametersXDD-Diff	OPTIONAL
}

MAC-ParametersCommon ::=	SEQUENCE {
	lcp-Restriction					ENUMERATED {supported}	OPTIONAL,

	pucch-SpatialRelInfoMAC-CE		ENUMERATED {supported}	OPTIONAL
}

MAC-ParametersXDD-Diff ::=	SEQUENCE {
	skipUplinkTxDynamic				ENUMERATED {supported}	OPTIONAL,
	logicalChannelSR-DelayTimer		ENUMERATED {supported}	OPTIONAL, 
	longDRX-Cycle					ENUMERATED {supported}	OPTIONAL, 
	shortDRX-Cycle					ENUMERATED {supported}	OPTIONAL, 
	multipleSR-Configurations		ENUMERATED {supported}	OPTIONAL, 
	
	
	multipleConfiguredGrantConfigurations	ENUMERATED {supported}	OPTIONAL 
	
	
	
}

MeasParameters ::= SEQUENCE {
	measParametersXDD-Diff			MeasParametersXDD-Diff		OPTIONAL,
	measParametersFRX-Diff			MeasParametersFRX-Diff		OPTIONAL
}

MeasParametersXDD-Diff ::=	SEQUENCE {
	intraAndInterF-MeasAndReport	ENUMERATED {supported}	OPTIONAL,
	eventA-MeasAndReport			ENUMERATED {supported}	OPTIONAL 
	
}

MeasParametersFRX-Diff ::=	SEQUENCE {

	ss-SINR-Meas						ENUMERATED {supported}		OPTIONAL,

	csi-RSRP-AndRSRQ-MeasWithSSB		ENUMERATED {supported}		OPTIONAL,

	csi-RSRP-AndRSRQ-MeasWithoutSSB		ENUMERATED {supported}		OPTIONAL,

	csi-SINR-Meas						ENUMERATED {supported}		OPTIONAL,

	csi-RS-RLM							ENUMERATED {supported}		OPTIONAL
}





RRC-TransactionIdentifier ::=		INTEGER (0..3)





maxBandComb								INTEGER ::=	65536	
maxBasebandProcComb						INTEGER ::=	65536	
maxNrofServingCells						INTEGER ::=	32		
maxNrofServingCells-1					INTEGER ::= 31		
maxNrofAggregatedCellsPerCellGroup		INTEGER ::= 16
maxNrofSCells							INTEGER ::=	31		
maxNrofCellMeas							INTEGER ::=	32		
maxNrofSS-BlocksToAverage				INTEGER ::= 16		
															
maxNrofCSI-RS-ResourcesToAverage			INTEGER ::= 16		
															
maxNrofDL-Allocations 					INTEGER ::= 16		

maxNrofSR-ConfigPerCellGroup				INTEGER ::= 8		

maxLCG-ID								INTEGER ::= 7		
maxLC-ID								INTEGER ::= 32		
maxNrofTAGs								INTEGER ::=	4		
maxNrofTAGs-1							INTEGER ::=	3		

maxNrofBWPs								INTEGER ::= 4		
maxNrofSymbols-1						INTEGER ::= 13		
maxNrofSlots							INTEGER ::= 320		
maxNrofSlots-1							INTEGER ::= 319		

maxNrofPhysicalResourceBlocks			INTEGER ::= 275		
maxNrofPhysicalResourceBlocks-1			INTEGER ::= 274		
maxNrofControlResourceSets 				INTEGER ::= 12 		
maxNrofControlResourceSets-1			INTEGER ::= 11  	
maxCoReSetDuration						INTEGER ::= 3		
maxNrofSearchSpaces						INTEGER ::= 40		
maxNrofSearchSpaces-1					INTEGER ::= 39		
maxSFI-DCI-PayloadSize					INTEGER ::= 128		
maxSFI-DCI-PayloadSize-1				INTEGER ::= 127		
maxINT-DCI-PayloadSize					INTEGER ::= 126		
maxINT-DCI-PayloadSize-1				INTEGER ::= 125		
maxNrofRateMatchPatterns				INTEGER ::= 4		
maxNrofRateMatchPatterns-1				INTEGER ::= 3		

maxNrofCSI-ReportConfigurations			INTEGER ::= 48 		
maxNrofCSI-ReportConfigurations-1		INTEGER ::= 47		

maxNrofCSI-ResourceConfigurations		INTEGER ::= 112		
maxNrofCSI-ResourceConfigurations-1		INTEGER ::= 111		

maxNrofAP-CSI-RS-ResourcesPerSet		INTEGER ::= 16
maxNrOfCSI-AperiodicTriggers			INTEGER ::= 128		
maxNrofReportConfigPerAperiodicTrigger	INTEGER ::= 16		

maxNrofNZP-CSI-RS-Resources				INTEGER ::= 192		
maxNrofNZP-CSI-RS-Resources-1			INTEGER ::= 191		
maxNrofNZP-CSI-RS-ResourcesPerSet		INTEGER ::= 64		
maxNrofNZP-CSI-RS-ResourceSetsPerConfig	INTEGER ::= 16		

maxNrofZP-CSI-RS-Resources				INTEGER ::= 32		
maxNrofZP-CSI-RS-Resources-1			INTEGER ::= 31		
maxNrofZP-CSI-RS-ResourceSets-1			INTEGER ::= 16
maxNrofZP-CSI-RS-ResourcesPerSet		INTEGER ::= 16
maxNrofZP-CSI-RS-Sets					INTEGER ::= 16

maxNrofCSI-IM-Resources					INTEGER ::= 32		
maxNrofCSI-IM-Resources-1				INTEGER ::= 31		
maxNrofCSI-IM-ResourcesPerSet			INTEGER ::= 8		
maxNrofCSI-IM-ResourceSetsPerConfig 	INTEGER ::= 16		

maxNrofSSB-Resources-1					INTEGER ::= 63		
maxNrofCSI-SSB-ResourcePerSet 			INTEGER ::= 64
maxNrofCSI-SSB-ResourceSetsPerConfig 	INTEGER ::= 1		

maxNrofFailureDetectionResources		INTEGER ::= 10		

maxNrofObjectId							INTEGER ::= 64		
maxNrofPCI-Ranges						INTEGER ::= 8		
maxNrofCSI-RS-ResourcesRRM				INTEGER ::= 96		
maxNrofCSI-RS-ResourcesRRM-1			INTEGER ::= 95		
maxNrofMeasId							INTEGER ::= 64		
maxNrofQuantityConfig					INTEGER	::= 2		
maxNrofCSI-RS-CellsRRM 					INTEGER ::= 96 		

maxNrofSRS-ResourceSets					INTEGER ::= 16		
maxNrofSRS-ResourceSets-1				INTEGER ::= 15		
maxNrofSRS-Resources					INTEGER ::= 64		
maxNrofSRS-Resources-1					INTEGER ::= 63		
maxNrofSRS-TriggerStates-1 				INTEGER ::= 3		
maxRAT-CapabilityContainers				INTEGER ::= 8		
maxSimultaneousBands					INTEGER ::= 32		


maxNrofSlotFormatCombinationsPerCell	INTEGER ::= 16		
maxNrofSlotFormatCombinationsPerSet		INTEGER ::= 4096	
maxNrofSlotFormatCombinationsPerSet-1	INTEGER ::= 4095	
maxNrofPUCCH-Resources					INTEGER ::= 128
maxNrofPUCCH-Resources-1				INTEGER ::= 127
maxNrofPUCCH-ResourceSets				INTEGER ::= 4		
maxNrofPUCCH-ResourceSets-1				INTEGER ::= 3		
maxNrofPUCCH-ResourcesPerSet			INTEGER ::= 32		
maxNrofPUCCH-ResourcesPerSet-1			INTEGER ::= 31		
maxNrofPUCCH-P0-PerSet					INTEGER ::= 8		
maxNrofPUCCH-PathlossReferenceRSs		INTEGER ::= 4		
maxNrofPUCCH-PathlossReferenceRSs-1		INTEGER ::= 3		

maxNrofP0-PUSCH-AlphaSets				INTEGER ::= 30		
maxNrofP0-PUSCH-AlphaSets-1				INTEGER ::= 29		
maxNrofPUSCH-PathlossReferenceRSs		INTEGER ::= 4		
maxNrofPUSCH-PathlossReferenceRSs-1		INTEGER ::= 3		

maxBands 								INTEGER ::= 1024		
maxBandsMRDC							INTEGER	::= 1280
maxBandsEUTRA							INTEGER ::=	256
maxCellPrep		 						INTEGER ::= 32
maxCellReport		 					INTEGER ::= 8
maxDRB		 							INTEGER ::= 29			
maxFreq		 							INTEGER ::= 8			
maxNrofCSI-RS	 						INTEGER ::= 64
maxNrofCandidateBeams 					INTEGER ::= 16			
maxNrofPCIsPerSMTC 						INTEGER ::= 64			
maxNrofQFIs 							INTEGER ::= 64
maxNrofSR-Resources		 				INTEGER ::= 8			
maxNrofSlotFormatsPerCombination 		INTEGER ::= 256
maxNrofSpatialRelationInfos 			INTEGER ::= 8
maxNrofSRS-ResourcesPerSet 				INTEGER ::= 16
maxNrofIndexesToReport 					INTEGER ::= 32
maxNrofSSBs 							INTEGER ::= 64 			
maxNrofSSBs-1							INTEGER ::= 63			

maxNrofTCI-StatesPDCCH 					INTEGER ::= 64
maxNrofTCI-States						INTEGER ::= 64			
maxNrofTCI-States-1						INTEGER ::= 63			
maxNrofUL-Allocations 					INTEGER ::= 16			
maxQFI 									INTEGER ::= 63
maxRA-CSIRS-Resources 					INTEGER ::= 96
maxRA-OccasionsPerCSIRS					INTEGER ::= 64			
maxRA-Occasions-1						INTEGER ::=	511			
maxRA-SSB-Resources 					INTEGER ::= 64
maxSCSs									INTEGER ::= 5
maxSecondaryCellGroups 					INTEGER ::= 3
maxNrofServingCellsEUTRA				INTEGER ::= 32
maxMBSFN-Allocations					INTEGER ::= 8
maxNrofMultiBands						INTEGER ::= 8
maxCellSFTD    	                    	INTEGER ::= 3  			
maxReportConfigId                 	 	INTEGER ::= 64

maxNrofSRI-PUSCH-Mappings				INTEGER ::= 16
maxNrofSRI-PUSCH-Mappings-1				INTEGER ::= 15


CellIdentity ::=						ENUMERATED {ffsTypeAndValue}
ShortMAC-I ::=							ENUMERATED {ffsTypeAndValue}




END



NR-UE-Variables DEFINITIONS AUTOMATIC TAGS ::=

BEGIN

IMPORTS
	MeasId,
	MeasIdToAddModList,
	MeasObjectToAddModList,
	PhysCellId,
	ReportConfigToAddModList,
	RSRP-Range,
	QuantityConfig,
	maxNrofCellMeas,
	maxNrofMeasId
FROM NR-RRC-Definitions;




VarMeasConfig ::=					SEQUENCE {
	
	measIdList							MeasIdToAddModList					OPTIONAL,
	
	measObjectList						MeasObjectToAddModList				OPTIONAL,
	
	reportConfigList					ReportConfigToAddModList			OPTIONAL,
	
	quantityConfig						QuantityConfig						OPTIONAL,
	
	s-MeasureConfig							CHOICE {
		ssb-RSRP								RSRP-Range,						
		csi-RSRP								RSRP-Range						
	} 																		OPTIONAL

}





VarMeasReportList ::=				SEQUENCE (SIZE (1..maxNrofMeasId)) OF VarMeasReport

VarMeasReport ::=					SEQUENCE {
	
	measId								MeasId,
	cellsTriggeredList					CellsTriggeredList				OPTIONAL,
	numberOfReportsSent					INTEGER
}

CellsTriggeredList ::=				SEQUENCE (SIZE (1..maxNrofCellMeas)) OF CHOICE {
	physCellId							PhysCellId,

	physCellIdEUTRA						ENUMERATED {ffsTypeAndValue}
	}





END




NR-InterNodeDefinitions DEFINITIONS AUTOMATIC TAGS ::=

BEGIN

IMPORTS
	ARFCN-ValueNR,
	CellIdentity,
	CSI-RS-Index,
	GapConfig,
	maxBandComb,
	maxBasebandProcComb,
	maxNrofSCells,
	maxNrofIndexesToReport,
	MeasQuantityResults,
	MeasResultSCG-Failure,
	MeasResultCellListSFTD,
	P-Max,
	PhysCellId,
	RadioBearerConfig,
	RRCReconfiguration,
	ServCellIndex,
	SSB-Index,
	ShortMAC-I,
	UE-CapabilityRAT-ContainerList
FROM NR-RRC-Definitions;





HandoverCommand ::=					SEQUENCE {
	criticalExtensions					CHOICE {
		c1									CHOICE{
			handoverCommand					HandoverCommand-IEs,
			spare3 NULL, spare2 NULL, spare1 NULL
		},
		criticalExtensionsFuture			SEQUENCE {}
	}
}

HandoverCommand-IEs ::=				SEQUENCE {
	handoverCommandMessage				OCTET STRING (CONTAINING RRCReconfiguration),
	nonCriticalExtension				SEQUENCE {}							OPTIONAL
}





HandoverPreparationInformation ::=	SEQUENCE {
	criticalExtensions					CHOICE {
		c1									CHOICE{
			handoverPreparationInformation		HandoverPreparationInformation-IEs,
			spare3 NULL, spare2 NULL, spare1 NULL
		},
		criticalExtensionsFuture			SEQUENCE {}
	}
}

HandoverPreparationInformation-IEs ::= SEQUENCE {
	ue-CapabilityRAT-List				UE-CapabilityRAT-ContainerList,
	sourceConfig						OCTET STRING (CONTAINING RRCReconfiguration),
	rrm-Config							RRM-Config				OPTIONAL,
	as-Context							AS-Context				OPTIONAL,
	nonCriticalExtension				SEQUENCE {}				OPTIONAL
}

AS-Context ::=							SEQUENCE {
	reestablishmentInfo						SEQUENCE {
		sourcePhysCellId					PhysCellId,
		targetCellShortMAC-I				ShortMAC-I,
		additionalReestabInfoList			ReestabNCellInfoList					OPTIONAL
	}																				OPTIONAL,
	
	configRestrictInfo					ConfigRestrictInfoSCG						OPTIONAL,
	...
}

ReestabNCellInfoList ::=		SEQUENCE ( SIZE (1..maxCellPrep) ) OF ReestabNCellInfo

ReestabNCellInfo::=	SEQUENCE{
	cellIdentity							CellIdentity,
	key-gNodeB-Star							BIT STRING (SIZE (256)),
	shortMAC-I								ShortMAC-I
}

RRM-Config ::=				SEQUENCE {
	ue-InactiveTime				ENUMERATED {
									s1, s2, s3, s5, s7, s10, s15, s20,
									s25, s30, s40, s50, min1, min1s20c, min1s40,
									min2, min2s30, min3, min3s30, min4, min5, min6,
									min7, min8, min9, min10, min12, min14, min17, min20,
									min24, min28, min33, min38, min44, min50, hr1,
									hr1min30, hr2, hr2min30, hr3, hr3min30, hr4, hr5, hr6,
									hr8, hr10, hr13, hr16, hr20, day1, day1hr12, day2,
									day2hr12, day3, day4, day5, day7, day10, day14, day19,
									day24, day30, dayMoreThan30}		OPTIONAL ,
	candidateCellInfoList		CandidateCellInfoList		OPTIONAL,
	...
}





CG-Config ::=					SEQUENCE {
	criticalExtensions					CHOICE {
		c1									CHOICE{
			cg-Config					CG-Config-IEs,
			spare3 NULL, spare2 NULL, spare1 NULL
		},
		criticalExtensionsFuture			SEQUENCE {}
	}
}

CG-Config-IEs ::=			SEQUENCE {
	scg-CellGroupConfig					OCTET STRING (CONTAINING RRCReconfiguration)	OPTIONAL,
	scg-RB-Config						OCTET STRING (CONTAINING RadioBearerConfig)		OPTIONAL,
	configRestrictModReq				ConfigRestrictModReqSCG							OPTIONAL,
	drx-InfoSCG							DRX-Info										OPTIONAL,
	candidateCellInfoListSN				OCTET STRING (CONTAINING CandidateCellInfoList)	OPTIONAL,
	measConfigSN						MeasConfigSN									OPTIONAL,
	selectedBandCombinationNR			BandCombinationIndex							OPTIONAL,
	nonCriticalExtension				SEQUENCE {}										OPTIONAL
}

MeasConfigSN ::= SEQUENCE {
	measuredFrequenciesFR1				SEQUENCE (SIZE (1..maxMeasFreqsMN))	OF NR-FreqInfo	OPTIONAL,
	...
}

NR-FreqInfo ::= SEQUENCE {
	measuredFrequency 					ARFCN-ValueNR									OPTIONAL,
	...
}

ConfigRestrictModReqSCG ::=			SEQUENCE {
	requestedBC-MRDC					BandCombinationIndex							OPTIONAL,
	requestedBPC-ListMRDC				BPC-IndexList									OPTIONAL,
	requestedP-MaxFR1				P-Max												OPTIONAL,
	...
}

BandCombinationIndex ::= INTEGER (1..maxBandComb)





CG-ConfigInfo ::=				SEQUENCE {
	criticalExtensions				CHOICE {
		c1								CHOICE{
			cg-ConfigInfo				CG-ConfigInfo-IEs,
			spare3 NULL, spare2 NULL, spare1 NULL
		},
		criticalExtensionsFuture		SEQUENCE {}
	}
}

CG-ConfigInfo-IEs ::=		SEQUENCE {
	ue-CapabilityInfo			OCTET STRING (CONTAINING UE-CapabilityRAT-ContainerList)		OPTIONAL, -- Cond SN-Addition
	candidateCellInfoListMN			CandidateCellInfoList									OPTIONAL,
	candidateCellInfoListSN			OCTET STRING (CONTAINING CandidateCellInfoList)			OPTIONAL,
	measResultCellListSFTD			MeasResultCellListSFTD									OPTIONAL,
	scgFailureInfo					SEQUENCE {
		failureType						ENUMERATED { t310-Expiry, randomAccessProblem,
														rlc-MaxNumRetx, scg-ChangeFailure, 
														scg-reconfigFailure,
														srb3-IntegrityFailure},
		measResultSCG					OCTET STRING (CONTAINING MeasResultSCG-Failure)
	}																						OPTIONAL,
	configRestrictInfo			ConfigRestrictInfoSCG										OPTIONAL,
	drx-InfoMCG					DRX-Info													OPTIONAL,
	measConfigMN				MeasConfigMN												OPTIONAL,
	sourceConfigSCG				OCTET STRING (CONTAINING RRCReconfiguration)				OPTIONAL,
	scg-RB-Config             	OCTET STRING (CONTAINING RadioBearerConfig)        			OPTIONAL,
	mcg-RB-Config				OCTET STRING (CONTAINING RadioBearerConfig)					OPTIONAL,
	nonCriticalExtension		SEQUENCE {}													OPTIONAL
}

ConfigRestrictInfoSCG ::=		SEQUENCE {
	allowedBC-ListMRDC				BandCombinationIndexList								OPTIONAL,
	allowedBPC-ListMRDC				BPC-IndexList											OPTIONAL,
	powerCoordination-FR1				SEQUENCE {
		p-maxNR							P-Max												OPTIONAL,
		p-maxEUTRA						P-Max												OPTIONAL
	}																						OPTIONAL,
	servCellIndexRangeSCG			SEQUENCE {
		lowBound						ServCellIndex,
		upBound							ServCellIndex
	}																						OPTIONAL,    -- Cond SN-Addition
	maxMeasFreqsSCG-NR					INTEGER(1..maxMeasFreqsMN)								OPTIONAL,
	...
}

BandCombinationIndexList ::= SEQUENCE (SIZE (1..maxBandComb)) OF BandCombinationIndex

BPC-IndexList ::= SEQUENCE (SIZE (1..maxBasebandProcComb)) OF BPC-Index
BPC-Index ::= INTEGER (1..maxBasebandProcComb)

DRX-Info ::=					SEQUENCE {
	drx-LongCycleStartOffset		CHOICE {
		ms10							INTEGER(0..9),
		ms20							INTEGER(0..19),
		ms32							INTEGER(0..31),
		ms40							INTEGER(0..39),
		ms60							INTEGER(0..59),
		ms64							INTEGER(0..63),
		ms70							INTEGER(0..69),
		ms80							INTEGER(0..79),
		ms128							INTEGER(0..127),
		ms160							INTEGER(0..159),
		ms256							INTEGER(0..255),
		ms320							INTEGER(0..319),
		ms512							INTEGER(0..511),
		ms640							INTEGER(0..639),
		ms1024							INTEGER(0..1023),
		ms1280							INTEGER(0..1279),
		ms2048							INTEGER(0..2047),
		ms2560							INTEGER(0..2559),
		ms5120							INTEGER(0..5119),
		ms10240							INTEGER(0..10239)
	},
	shortDRX							SEQUENCE {
		drx-ShortCycle						ENUMERATED	{
												ms2, ms3, ms4, ms5, ms6, ms7, ms8, ms10, ms14, ms16, ms20, ms30, ms32,
												ms35, ms40, ms64, ms80, ms128, ms160, ms256, ms320, ms512, ms640, spare9,
												spare8, spare7, spare6, spare5, spare4, spare3, spare2, spare1 },
		drx-ShortCycleTimer					INTEGER (1..16)
	}																					OPTIONAL
}

MeasConfigMN ::= SEQUENCE {
	measuredFrequenciesMN				SEQUENCE (SIZE (1..maxMeasFreqsMN))	OF NR-FreqInfo	OPTIONAL,
	measGapConfigFR1					GapConfig											OPTIONAL,
	gapPurpose							ENUMERATED {perUE, perFR1}							OPTIONAL,
	...
}






MeasurementTimingConfiguration ::=				SEQUENCE {
	criticalExtensions				CHOICE {
		c1								CHOICE{
			measTimingConf					MeasurementTimingConfiguration-IEs,
			spare3 NULL, spare2 NULL, spare1 NULL
		},
		criticalExtensionsFuture		SEQUENCE {}
	}
}

MeasurementTimingConfiguration-IEs ::=	SEQUENCE {
	measTiming								MeasTimingList							OPTIONAL,
	nonCriticalExtension					SEQUENCE {}								OPTIONAL
}

MeasTimingList ::= SEQUENCE (SIZE (1..maxMeasFreqsMN)) OF MeasTiming  

MeasTiming ::= SEQUENCE {
	carrierFreq								ARFCN-ValueNR							OPTIONAL,         
	ssb-MeasurementTimingConfiguration		ENUMERATED {ffsTypeAndValue}		OPTIONAL,
	...
}





CandidateCellInfoList ::=	SEQUENCE (SIZE (1.. maxNrofSCells)) OF CandidateCellInfo

CandidateCellInfo ::=			SEQUENCE {
	cellIdentification				SEQUENCE {
		physCellId						PhysCellId,
		dl-CarrierFreq					ARFCN-ValueNR
	},
	measResultCell					MeasQuantityResults											OPTIONAL,
	candidateRS-IndexListSSB		CandidateRS-IndexInfoListSSB								OPTIONAL,
	candidateRS-IndexListCSI-RS		CandidateRS-IndexInfoListCSI-RS								OPTIONAL,
	...
}

CandidateRS-IndexInfoListSSB ::=	SEQUENCE (SIZE (1..maxNrofIndexesToReport)) OF CandidateRS-IndexInfoSSB

CandidateRS-IndexInfoSSB ::=	SEQUENCE {
	ssb-Index						SSB-Index,
	measResultSSB					MeasQuantityResults											OPTIONAL,
	...
}

CandidateRS-IndexInfoListCSI-RS ::=	SEQUENCE (SIZE (1..maxNrofIndexesToReport)) OF CandidateRS-IndexInfoCSI-RS

CandidateRS-IndexInfoCSI-RS ::=		SEQUENCE {
	csi-RS-Index							CSI-RS-Index,
	measResultCSI-RS						MeasQuantityResults									OPTIONAL,
	...
}





maxMeasFreqsMN				INTEGER ::= 32	
maxCellPrep					INTEGER ::= 32	





END
